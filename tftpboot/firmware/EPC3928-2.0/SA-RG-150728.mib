--**************************************************************************
--**************************************************************************
--
--    Copyright 2011 Cisco Systems, Inc.
--    All Rights Reserved
--    No portions of this material may be reproduced in any
--    form without the written permission of:
--        Cisco Systems, Inc.
--        170 West Tasman Dr.
--        San Jose, CA 95134
--        USA
--
--**************************************************************************

SA-RG-MIB DEFINITIONS ::= BEGIN
IMPORTS
        MODULE-IDENTITY,
        OBJECT-TYPE,
        enterprises,
        Integer32,
        IpAddress
                FROM SNMPv2-SMI
        ifIndex
                FROM IF-MIB
        RowStatus,
        DisplayString,
        MacAddress,
        PhysAddress,
        TruthValue,
        DateAndTime
                FROM SNMPv2-TC
        InetAddressType,
        InetAddress,
                InetAddressIPv6,
        InetPortNumber
                FROM INET-ADDRESS-MIB
        SnmpAdminString
                FROM SNMP-FRAMEWORK-MIB ;

sa           OBJECT IDENTIFIER ::= { enterprises 1429 }
saModules    OBJECT IDENTIFIER ::= { sa 79 }

saRg    MODULE-IDENTITY
        LAST-UPDATED    "201403250000Z"
        ORGANIZATION    "Cisco Systems, Inc."
        CONTACT-INFO    "http://support.cisco.com"
        DESCRIPTION
            "Controls the behavior of router/wireless functions.
             Can be part of CM configuration file."

        -- History
        REVISION "201403250000Z"
	DESCRIPTION "Added 
				saRgIpMgmtDnsServerIpv6 (CR23803)
				saRgDot11ClientConnectMode (CR23649)
				saRgFirewallIpv6Protection (CR23798)
				saRgDot11BssRejectPriSsidStaCount (CR23390)
				saRgIpMgmtLanAddrIpv6Table (CR24093)
				"
		
        REVISION "201402180000Z"
	DESCRIPTION "Added bitmask on WebWizard for USB setting, NAS and media server tab(23504)"
	             
                   
		REVISION "201401160000Z"
	DESCRIPTION "Changed saRgWifiHotspotInsertDhcpOptionsMask. Added option for CM MAC address included in DHCP option 82.2 (CR23343)"
			
		REVISION "201401140000Z"
	DESCRIPTION "Add rgPortForward(3) to saRgDeviceConfigSnmpEnable(CR23485)"
		
		REVISION "201312190000Z"
	DESCRIPTION "Added saRgDot11BssPrimarySsidSuffix, saRgWifiHotspotDisablePMKCaching, saRgWifiHotspotConnectionSpeedMin, saRgWifiHotspotConnectionSpeedTimeout, saRgWifiHotspotRadiusAccInterimInterval"

                REVISION "201311050000Z"
	DESCRIPTION "Modified values and description for saRgDot11nMode/nExtMode"

                REVISION "201309200000Z"
	DESCRIPTION "Added support for saRgNetworkExtenders MIB
                Added:  saRgNetworkExtenderTable
                        saRgNetworkExtenderRadioTable
                        saRgNetworkExtenderClientTable"

                REVISION "201309170000Z"
	DESCRIPTION "Modified Values and description for
                   saRgDot11nMode
                   saRgDot11nExtMode"

                REVISION "201308280000Z"
	DESCRIPTION "Added WiFi 2.4 and 5 Ghz support for saRgIpMgmtLanAddrInterface MIB

                Added: saRgFirewallPortForwardEnable
                saRgFirewallPortTriggerEnable
                saRgFirewallIpFilterTrusted
                saRgFirewallIpFilterPolicy
                saRgFirewallPortFilterAlwaysBlock
                saRgFirewallPortFilterBlockStartTime
                saRgFirewallPortFilterBlockEndTime
                saRgFirewallPortFilterBlockDays
                saRgFirewallMacFilterAlwaysBlock
                saRgFirewallMacFilterBlockStartTime
                saRgFirewallMacFilterBlockEndTime
                saRgFirewallMacFilterBlockDays
                saRgFirewallPortFilterEnable
                saRgFirewallUrlKeywordFilterTable
                saRgFirewallUrlKeywordFilterEnable"

                REVISION "201308270000Z"
        DESCRIPTION "Added saRgDot11ApsScan MIB tree"

                REVISION "201308140000Z"
        DESCRIPTION "Added saRgDeviceIanaContent, saRgDeviceIapdContent"

                REVISION "201308070000Z"
        DESCRIPTION "Added saRgIGMP, saRgIGMPMaxRspTime"

                REVISION "201307220000Z"
        DESCRIPTION "Added saRgL2ogreKeepAliveFailureInterval, saRgL2ogreKeepAliveReattemptInterval, saRgWifiHotspotCapable and saRgWifiHotspotConnectedClientsTable"

        REVISION "201306240000Z"
        DESCRIPTION "Added saRgIpMgmtWanStaticNameServerEnable, saRgIpMgmtWanStaticHostName, saRgIpMgmtWanStaticDomainName"

        REVISION "201306110000Z"
        DESCRIPTION "Added saRgFirewallIdentBlockingEnable, saRgFirewallIcmpBlockingEnable, saRgFirewallMulticastBlockingEnable"

        REVISION "201306070000Z"
        DESCRIPTION "Modified saRgdot11nBandWidth and saRgdot11nExtBandWidth to include support for 80MHz BW on 802.11ac cards"

  REVISION "201305010000Z"
  DESCRIPTION "Added saRgDeviceIpv6Passthrough"

  REVISION "201303040000Z"
  DESCRIPTION "Added saRgL2TPv3TunnelInterface value allEthernet(0) and updated the description"

        REVISION "201301020000Z"
        DESCRIPTION "Added saRgRipAuthType and saRgRipAuthSimplePassword"

        REVISION "201212070000Z"
        DESCRIPTION "Addes saRgDot11ChannelSelectionPolicy"

    REVISION "201211070000Z"
    DESCRIPTION "Added saRgFirewallPortFwdExternalPortStart and saRgFirewallPortFwdExternalPortEnd"

    REVISION "201210010000Z"
    DESCRIPTION "Modified saRgL2ogreOrigIf"

        REVISION "201209190000Z"
    DESCRIPTION "Added saRgIpMgmtLanDhcpOption43"

    REVISION "201209190000Z"
    DESCRIPTION "Added saRgFirewallPortTrigSrvcName, changed saRgDot11BssSecSsidTrafficPriority value 1 to acBk"

    REVISION "201209100000Z"
    DESCRIPTION "Added saRgFirewallPortFwdSrvcName to saRgFirewallPortFwdEntry"

    REVISION "201209070000Z"
    DESCRIPTION "Updated saRgFirewallProtection with custom(4), and saRgFirewallTrafficPassThru with ident(3) and icmp(4)"

    REVISION "201208270000Z"
    DESCRIPTION "Added saRgDot11BssRejectPriSsidSta (21104)"

    REVISION "201208270000Z"
    DESCRIPTION "Added saRgDot11BssSecSsidTrafficPriority (20232)"

    REVISION "201208230000Z"
    DESCRIPTION "Corrected syntax errors in saRgDeviceFactoryReset and saRgDeviceReset
                        Modified saRgDot11BssMaxNumSta from read-only to read-write"

    REVISION "201207250000Z"
    DESCRIPTION "Modified the default values of saRgDot11WpaGroupRekeyInterval and saRgDot11RadiusReAuthInterval - CR 21057"

    REVISION "201207120000Z"
    DESCRIPTION "Added: saRgIpMgmtWanAddrDynamicIp
                                                saRgIpMgmtWanAddrDynamicLeaseTime
                                                saRgFirewallFactoryReset
                                                saRgFirewallHttpBlockingEnable
                                                saRgFirewallP2pBlockingEnable
                                                saRgIpMgmtLanAddrClientNotes
                                                saRgIpMgmtLanAddrCpeStatus
                                                saRgIpMgmtLanDhcpServerDomainName
                                                saRgDeviceFactoryReset
                                                saRgDeviceReset"

    REVISION "201207110000Z"
    DESCRIPTION "Added plain/encapsulation mode mappings to the saRgDslitePcpMode description"

    REVISION "201207010000Z"
    DESCRIPTION "ADDED saRgWifiHotspot MIB tree
                         ADDED saRgL2oGRE MIB tree"

    REVISION "201206140000Z"
    DESCRIPTION "Modified the data types of saRgIpMgmtNatTcpWait, saRgIpMgmtNatUdpWait, and saRgIpMgmtNatIcmpWait from INTEGER to Unsigned32 - CR 20790"

    REVISION "201206120000Z"
    DESCRIPTION "Fixed small error in comments causing compile problems"

    REVISION "201204160000Z"
    DESCRIPTION "Removed saRgDot1154gNetMode and saRgDot11Ext54gNetMode - CR 20357/19913"

    REVISION "201203160000Z"
    DESCRIPTION "Added saRgDot11ExtCtsProtectionEnable and removed saRgdot11Ext54gProtectionEnable/nExtProtection. Also, added the n-only(3) option in saRgdot11nMode/nExtMode - CR 20227/20246"

    REVISION "201203080000Z"
    DESCRIPTION "Modified saRgIpMgmtLanUpnp to indicate UPnP control is now available for all networks - CR 19832"

    REVISION "201203060000Z"
    DESCRIPTION "Added saRgDot11ExtMgmt and saRgDot11nExt trees for multi-radio operation - CR 20227"

    REVISION "201203050000Z"
    DESCRIPTION "Added saRgDslitePcpMode MIB - CR20218"

    REVISION "201202010000Z"
    DESCRIPTION "Added saRgIpMgmtLanAddrInterface - CR -- 19894"

    REVISION "201201190000Z"
    DESCRIPTION "Updated saRgDsliteTcpMssClamping and saRgDsliteIPv4FragEnabled description -- CR 19941"

    REVISION "201201180000Z"
    DESCRIPTION "Added saRgDsliteTcpMssClamping and saRgDsliteIPv4FragEnabled -- CR 19941"

    REVISION "201112150000Z"
    DESCRIPTION "Changed default value of saRgVlanStripTagsWan to true - CR 18055
                Updated saRgDot11WmmNoAck MIB descriptions --CR 18824"

    REVISION "201111220000Z"
    DESCRIPTION "Updated saRgDot11Wmm and saRgDot11WmmNoAck MIB descriptions --CR 18824"

    REVISION "201111170000Z"
    DESCRIPTION "Changed saRgDeviceIpv6Trans to read-only, updated description to reflect new behavior"

    REVISION "201111160000Z"
    DESCRIPTION "Removed option-54(2) from saRgDsliteOption"

    REVISION "201111100000Z"
    DESCRIPTION "Added saRgIpMgmtLanExtraSubnetGateway.x and changed saRgIpMgmtLanExtraSubnetIpAddress from
    read-only to read-write access. -- CR 19474.
    Added saRgDot11WirelessButtonOperation : Wireless ON/OFF Button Operation (if exit) --CR 19443.
    Updated description of saRgDot11BssUserStatus."

    REVISION "201110270000Z"
    DESCRIPTION "Added saRgDeviceIpv6Trans, saRgDsliteOption, saRgDsliteAftrAddress, saRgDsliteAftrName, saRgDsliteApplySettings - CRs 19548, 19572, 19573, 19576, 19586"

    REVISION "201110190000Z"
    DESCRIPTION "Removed saRgVlanIndex.x -- CR 18055
    Added saRgDeviceLanLanIsolation, saRgDeviceLanWlanIsolation and saRgDot11BssApIsolation -- CR 15633"

    REVISION "201110060000Z"
    DESCRIPTION "Updated description for saRgDot11MbssUserControl and saRgDot11MbssAdminControl
    Support for utilizing Bit16 and above as a bit mask value for allowing/disallowing MBSS configuration"

    REVISION "201109280000Z"
    DESCRIPTION "Updated saRgFirewallTrafficBlock and saRgFirewallProtection (Updated low/ enable in desc) MIB description -- CR 19428"

    REVISION "201109070000Z"
    DESCRIPTION "Updated saRgDevUserLanAccessEnabled MIB definition."

    REVISION "201109060000Z"
    DESCRIPTION "Updated saRgDevUserLanAccessEnabled MIB definition CR-19105. This MIB is only available for D2.0"

    REVISION "201108030000Z"
    DESCRIPTION "Updated MIB descriptions for saRgIpMgmtLanMode, saRgVlanStripTagsWan and saRgVlanStripTagsLan CR-18556"

    REVISION "201107250000Z"
    DESCRIPTION "Added clarification about saRgIpMgmtLanNetworksAllow MIB behavior when the
    MIB value is a default value - CR 188670"

    REVISION "201107110000Z"
    DESCRIPTION "Added saRgFirewallMacFilterEnable and saRgFirewallMacFilterMode to sync with MAC Address Filter
    Web GUI controls - CR 17542
    Added saRgDot11Wmm MIB to enable/disable Wifi Multi Media QOS feature -CR 18824
    Added saRgDot11WmmNoAck MIB to enable/disable Wifi Multimedia No Acknowledgement feature -CR 18824
    Added saRgVlanUpnp and saRgVlanApplySettings MIBs- CR 18055
    Added saRgDot11BssHotSpot to saRgDot11BssEntry per CR 18153
    Added saRgDot11MulticastRate and saRgdot11nMulticastRate mulitcast rate configuration MIBs -CR 18899."

    REVISION "201107010000Z"
    DESCRIPTION "Added saRgDot11BssUserStatus mibs for 18263"

    REVISION "201106100000Z"
    DESCRIPTION "Added saRgVlan mibs and added vlan(5) control option to saRgIpMgmtLanMode CR 18055"

    REVISION "201106070000Z"
    DESCRIPTION "Updated saRgIpMgmtLanMode MIB description to indicate Mixed Mode support NOT AVAILABLE for DOCSIS 2.0 products."

    REVISION "201105020000Z"
    DESCRIPTION "Added saRgdot11nObssCoex to saRgDot11n tree"

        REVISION "201104210000Z"
        DESCRIPTION "Modified the index size for saRgFirewallMacFilterIndex from 10 to 20 - CR 17294
                     Updated the index size for saRgFirewallPortFwdIndex from 10 to 30 - CR 17891"

        REVISION "201102080000Z"
        DESCRIPTION "Modified the list size saRgDot11CurrentChannel to reflect channels supported in 802.11n 2.4 & 5 GHz band"

    REVISION "201101190000Z"
    DESCRIPTION "Changed saRgDeviceRemoteWebAccessPort MIB to be stored in non-vol"

    REVISION "201101100000Z"
    DESCRIPTION "BAC RG-MIB compile issue. Removed an extra ',' in the saRgQosSwitchClassPrioritySetPort MIB"

        REVISION "201012200000Z"
        DESCRIPTION "i) Changed ip_mac_portFiltering(7) to ipMacPortFiltering(7) in SaRgUserChangedFlag
                        As the MIB tool will report an error for the use of '_'"

        REVISION "201011300000Z"
        DESCRIPTION "Added saRgIpMgmtRestoreDefaults"

    REVISION "201011160000Z"
    DESCRIPTION "i) Updated saRgDeviceMode
                    ii) Updated saRgIpMgmtLanMode "

    REVISION "201010190000Z"
    DESCRIPTION "i) Added l2TP(25) under SaRgUserChangedFlag for L2TP feature
                     ii)Added ethernet(1..4) under saRgL2TPv3TunnelInterface MIB"

    REVISION "201010070000Z"
    DESCRIPTION "i) Updated saRgDeviceL2TP to saRgL2TP for all the MIBs under saRgL2TP tree "

    REVISION "201010060000Z"
        DESCRIPTION "i) saRgDeviceMode modified for eRouter CR17253
                                        Added values (3)ipv4, (4)ipv6, and (5)dualstack.
                                        Added default value (1)
                                        Updated description to clarify interaction with TLV202
                    ii) saRgIpMgmtLanMode  modified for eRouter CR17253
                                        Clarified description
                                        Added Default value (2)
                   iii) saRgDeviceConfigSnmpEnable modified for eRouter CR17253
                                        Updated description (ipv4RG only)"

    REVISION "201010050000Z"
        DESCRIPTION "i)Added a saRgDeviceL2TP MIB tree under saRg 10 - CR17249
                    ii)saRgIpMgmtLanMode no longer supports l2tp-client(3)
                   iii)saRgIpMgmtL2tpClientTable is obsoleted and will not be supported"


    REVISION "201009020000Z"
        DESCRIPTION "Updated description for saRgIpMgmtLanPortMode"

    REVISION "201009020000Z"
        DESCRIPTION "Updated description for saRgDot11MbssUserControl and saRgDot11MbssAdminControl
        support for 8 SSIDs"

    REVISION "201008230000Z"
    DESCRIPTION "Renamed saRgDeviceLanPortControl MIB tree to saRgIpMgmtLanPortControl
                                 and moved saRgDeviceLanPortControl MIB tree under saRgIpMgmt"

    REVISION "201008200000Z"
    DESCRIPTION "Added value mixed(4) to saRgIpMgmtLanMode,
                        Added saRgDeviceLanPortControl MIB tree"

        REVISION "201008130000Z"
        DESCRIPTION " Increase the range of the saRgDot11MbssUserControl and saRgDot11MbssAdminControl from
        1..4 to 1..8 to support 8 SSIDs"

        REVISION "201007300000Z"
        DESCRIPTION "Add rgLanIp(2) to saRgDeviceConfigSnmpEnable"

        REVISION     "201007280000Z"
        DESCRIPTION
             "Added saRgHomePlugAV module under saRg {saRg 9} which includes the following tables (16664)
             1. saRgHomePlugAVBasicInfoTable
                This table provides network id of Home Plug AV device on the AVLN and CCO information.
             2. saRgHomePlugAVDeviceTable
                This table shows firmware version, MAC address of Home Plug AV device, chipset, Tx rate,
                Rx rate and other information. Besides providing local Home Plug AV device information
                (saRgHPAVDeviceAdaptor OID = ‘local’), the table also provides remote Home Plug AV device
                information (saRgHPAVDeviceAdaptor OID = ‘remote’).
             3. saRgHomePlugAVHostTable
                This table provides bridge MAC address information of Home Plug AV device that are connected
                with Ethernet port behind RG.
             4. Operation OIDs
                These OIDs include saRgHomePlugAVPollRate, saRgHomePlugAVClearTable and
                saRgHomePlugAVRefreshTable, which provide operations on manipulation of above tables
                to scan Home Plug AV devices or to clear (reset) saRgHomePlugAVBasicInfoTable,
                saRgHomePlugAVDeviceTable and saRgHomePlugAVHostTable."


        REVISION     "201007120000Z"
    DESCRIPTION
             "Updated saRgDeviceConfigSnmpEnable to allow SNMP access on RG LAN side.(16317)
              Added saRgIpMgmtLanUpnp to control the UPnP agent (16623)"

    REVISION     "201006240000Z"
    DESCRIPTION
             "Added saRgIpMgmtLanNetworksAllow to control the classes of Lan Networks allowed
              behind the router (16626)"

    REVISION     "201006150000Z"
    DESCRIPTION
             "Changing the bits in SaRgUserChangedFlag as per the current
             implementation"

    REVISION     "201006040000Z"
    DESCRIPTION
             "Correcting the description in saRgDot1154gNetMode. Correcting
             the values in SaRgUserChangedFlag "


    REVISION     "201005210000Z"
    DESCRIPTION
             "saRgDeviceRemoteWebAccessEnable is applicable for legacy web
             pages. So making the status as current from obsolete and adding
             a note that it is only applicable for legacy style web pages"


    REVISION     "201005130000Z"
    DESCRIPTION
             "Updated the SaRgUserChangedFlag and saRgDeviceUserChangedFlag
                 by adding the relavent sections that were missing in the web pages
             and added a note for the behavior of MIB on the legacy style web
             pages"

    REVISION     "201005050000Z"
    DESCRIPTION
             "Moved the relavent Web Access MIBs to SA-CM.mib and obsoleted
             SaRgWebWizardSetup2,
             saRgDeviceUserAccessReadPages2,
             saRgDeviceUserAccessWritePages2,
             saRgDeviceAdminReadOnly,
             saRgDevUserLanAccessEnabled,
             saRgDeviceRemoteWebAccessEnable,
             saRgDevUserAccessClearPassword,
             saRgDevUserAccessDefaultPassword,
             saRgDevUserAccessUsername
             "

    REVISION     "201003120000Z"
    DESCRIPTION
             "Added saRgDot11OnOffPushButtonTime (15869)"

    REVISION     "201002010000Z"
    DESCRIPTION
             "Added saRgIpMgmtWanAddrBackupDefGw (15736)
              Changed saRgIpMgmtStaticRouteTable to be stored in non-vol (4213)
              Added saRgFirewallReportEmailUsername (15735)
              Added saRgFirewallReportEmailPassword (15735)"

    REVISION     "200912140000Z"
    DESCRIPTION
             "Added saRgDeviceConfigIgnore (3203)
              Changed saRgIpMgmtWanTtl DEFVAL to 0 (4630)
              Added enableOnline(3) to saRgDot11BssEnable (4614)
              Added saRgDot11BssMaxNumSta (4615)
              Added saRgDot11BssCountStaAsCpe (4617)
              Added saRgFirewallWANBlockingEnable (4743)
              Changed saRgDevUserAccessEnabled to saRgDevUserLanAccessEnabled (4854)
              Added remoteAccess(30) to SaRgWebWizardSetup (4855)
              Added variables to SaRgWebWizardSetup2 (4858)
              Added saRgQosLanIgmpSnooping (4891)
              Added saRgIpMgmtLanDhcp125Option (15007)
              Added saRgDeviceAdminReadOnly (15056)"

    REVISION     "200907240000Z"
    DESCRIPTION
             "Added saRgDevUserAccessUsername (4274)
              Added saRgDeviceUserChangedFlag (3301)"

    REVISION     "200907060000Z"
    DESCRIPTION
             "Added saRgDeviceConfigSnmpEnable (4167,4168)"

    REVISION     "200907020000Z"
    DESCRIPTION
             "Added SaRgWebWizardSetup2
              Obsoleted SaRgWebWizardSetup
              Added saRgDeviceUserAccessReadPages2
              Added saRgDeviceUserAccessWritePages2
              Obsoleted saRgDeviceUserAccessReadPages
              Obsoleted saRgDeviceUserAccessWritePages (4131, 4858)"

    REVISION     "200906240000Z"
    DESCRIPTION
             "Added saRgDot11n tree (4067)"

    REVISION     "200906020000Z"
    DESCRIPTION
             "Added l2tp-client(3) to saRgIpMgmtLanMode (3200)
              Added saRgIpMgmtL2tpClientTable (3200)
              Added saRgQos (4065)"

    REVISION     "200902160000Z"
    DESCRIPTION
             "Removed maxCompatibility(5) from saRgDot1154gNetMode (3200)"

    REVISION     "200809300000Z"
    DESCRIPTION
            "Changed saRgIpMgmtDnsServerIp to store in non-vol (2623)
             Added saRgIpMgmtPassthroughTable (2954)
             Added saRgIpMgmtLanExtraSubnetTable (2980)
             Added saRgFirewallMacFilterTable (3254)
             Changes saRgDot11PrivacyWpsPushButtonTime default to 1 (3278)"

    REVISION     "200806060000Z"
    DESCRIPTION
            "Added saRgDeviceTimeSetup (2629)
             Added saRgDot11PrivacyWpsPushButtonTime (2632)"

    REVISION     "200806020000Z"
    DESCRIPTION
            "Added firewall tree (2607)
             Added saRgIpMgmtWanMtu (2608)
             Added saRgIpMgmtWanTtl (2608)"

    REVISION     "200805270000Z"
    DESCRIPTION
            "Added saRgIpMgmtWanAddr (2595)"

    REVISION     "200804300000Z"
    DESCRIPTION
            "Initial release"

        ::= { saModules 2 }


SaRgWebWizardSetup ::= TEXTUAL-CONVENTION
    STATUS       obsolete
    DESCRIPTION
         "WebWizard Setup sections."
    SYNTAX BITS {
        basicPasswordSettings(0),
        basicSetTime(1),
        basicNetworkConfiguration(2),
        basicLAN(3),
        basicFixedCPE(4),
        basicRestart(5),
        basicSaveConfigurationPC(6),
        advancedOptions(7),
        advancedIPFiltering(8),
        advancedMACFiltering(9),
        advancedPortFiltering(10),
        advancedPortForwarding(11),
        advancedPortTriggers(12),
        advancedDMZ(13),
        advancedPassThrough(14),
        advancedNetworkingFeatures(15),
        advancedVPN(16),
        advancedSaveConfigurationServer(17),
        firewallOptions(18),
        firewallEvent(19),
        parentalUserSetup(20),
        parentalBasicRules(21),
        parentalTODRules(22),
        parentalLocalLog(23),
        wirelessBasic(24),
        wirelessSecurity(25),
        wirelessAdvanced(26),
        wirelessAccessControl(27),
        wirelessBridging(28),
        wirelessMultimedia(29),
        basicDDNS(30),
        remoteAccess(31)
        }

SaRgWebWizardSetup2 ::= TEXTUAL-CONVENTION
    STATUS       obsolete
    DESCRIPTION
         "WebWizard Setup sections."
    SYNTAX BITS {
        bridgeRouterMode(0),
        docsisSignal(1),
        docsisStatus(2),
        docsisLog(3),
        --timeUseNtp(4),
        timeZone(5),
        timeDst(6),
        --timeServer(7),
        lanIp(8),
        lanDhcpEnable(9),
        lanDhcpScope(10),
        lanDhcpLeaseTime(11),
        lanDhcpDns(12),
        --lanDhcpWins(13),
        lanFixedCpe(14),
        wanStaticIp(15),
        wanDns(16),
        wanMtu(17),
        --wanHostDomainNames(18),
        --resetModem(19),
        resetFactoryDefaults(20),
        backupConfigToPc(21),
        ddns(22),
        wanBlocking(23),
        ipsecPassthrough(24),
        pptpPassthrough(25),
        remoteManagement(26),
        --multicastPassthrough(27),
        upnpEnable(28),
        ipFiltering(29),
        macFiltering(30),
        portFiltering(31),
        portForwarding(32),
        portTriggers(33),
        dmz(34),
        vpnTermination(35),
        --staticRoute(36),
        firewallFilterProxy(37),
        firewallFilterCookies(38),
        firewallFilterJavaApplets(39),
        firewallFilterActiveX(40),
        firewallFilterPopupWindows(41),
        firewallBlockFragmentedPackets(42),
        portScanDetection(43),
        ipFloodDetection(44),
        firewallProtection(45),
        --firewallEventLogging(46),
        parentalControl(47),
        wireless2p4SSID(48),
        wireless2p4ABGNMode(49),
        wireless2p4SSID(50),
        wireless2p4BroadcastSSID(51),
        wireless2p4Channel(52),
        wireless2p4ChannelWidth(53),
        wireless2p4Security(54),
        wireless2p4Wps(55),
        wireless2p4Advanced(56),
        wireless2p4AccessControl(57),
        wireless2p4Bridging(58),
        wireless2p4Wmm(59),
        wireless2p4AckEnable(60),
        wireless5Enable(61),
        wireless5ABGNMode(62),
        wireless5SSID(63),
        wireless5BroadcastSSID(64),
        wireless5Channel(65),
        wireless5ChannelWidth(66),
        wireless5Security(67),
        wireless5Wps(68),
        wireless5Advanced(69),
        wireless5AccessControl(70),
        wireless5Bridging(71),
        wireless5Wmm(72),
        wireless5AckEnable(73),
        ping(74),
        igmpProxy(75),
        usbSetting(76),
        nas(77),
        mediaServer(78)
        }

SaRgTimeZone ::= TEXTUAL-CONVENTION
    STATUS       current
    DESCRIPTION
         "Time zones."
    SYNTAX INTEGER {
        gmtMinusTwelveEniwetokKwajalein(1),
        gmtMinusElevenMidwayIslandSamoa(2),
        gmtMinusTenHawaii(3),
        gmtMinusNineAlaska(4),
        gmtMinusEightPacificTimeCanadaTijuana(5),
        gmtMinusSevenArizona(6),
        gmtMinusSevenMountainTimeCanada(7),
        gmtMinusSixCentralAmerica(8),
        gmtMinusSixCentralTimeCanada(9),
        gmtMinusSixMexicoCity(10),
        gmtMinusSixSaskatchewan(11),
        gmtMinusFiveBogotaLimaQuito(12),
        gmtMinusFiveEasternTimeCanada(13),
        gmtMinusFiveIndianaEast(14),
        gmtMinusFourAtlanticTimeCanada(15),
        gmtMinusFourCaracasLaPaz(16),
        gmtMinusFourSantiago(17),
        gmtMinusThreeThirtyNewfoundland(18),
        gmtMinusThreeBrasilia(19),
        gmtMinusThreeBuenosAiresGeorgetown(20),
        gmtMinusThreeGreenland(21),
        gmtMinusTwoMid-Atlantic(22),
        gmtMinusOneAzores(23),
        gmtMinusOneCapeVerdeIs(24),
        gmtZeroCasablancaMonrovia(25),
        gmtZeroDublinEdinburghLisbonLondon(26),
        gmtPlusOneAmsterdamBerlinRomeStockholmVienna(27),
        gmtPlusOneBelgradeBratislavaBudapestLjubljanaPrague(28),
        gmtPlusOneBrusselsCopenhagenMadridParis(29),
        gmtPlusOneSarajevoSkopjeSofijaVilniusWarsawZagreb(30),
        gmtPlusOneWestCentralAfrica(31),
        gmtPlusTwoAthensIstanbilMinsk(32),
        gmtPlusTwoBucharest(33),
        gmtPlusTwoHelsinkiRigaTallinn(34),
        gmtPlusTwoJerusalem(35),
        gmtPlusThreeBaghdad(36),
        gmtPlusThreeMoscowStPetersburgVolgograd(37),
        gmtPlusThreeNairobi(38),
        gmtPlusThreeThirtyTehran(39),
        gmtPlusFourAbuDhabiMuscat(40),
        gmtPlusFourThirtyKabul(41),
        gmtPlusFiveEkaterinburg(42),
        gmtPlusFiveThirtyCalcuttaChennaiMumbaiNewDelhi(43),
        gmtPlusFiveFourtyFiveKathmandu(44),
        gmtPlusSixAlmatyNovosibirsk(45),
        gmtPlusSixAstanaDhaka(46),
        gmtPlusSixThirtyRangoon(47),
        gmtPlusSevenBangkokHanoiJakarta(48),
        gmtPlusSevenKrasnoyarsk(49),
        gmtPlusEightBeijingChongqingHongKongUrumqi(50),
        gmtPlusEightIrkustkUlaanBataar(51),
        gmtPlusEightKualaLumpurSingapore(52),
        gmtPlusEightTaipei(53),
        gmtPlusNineOsakaSapporoTokyo(54),
        gmtPlusNineSeoul(55),
        gmtPlusNineThirtyAdelaide(56),
        gmtPlusTenBrisbane(57),
        gmtPlusTenVladivostok(58),
        gmtPlusElevenMagadanSolomonIsNewCaledonia(59),
        gmtPlusTwelveAucklandWellington(60),
        gmtPlusTwelveFiji(61),
        gmtPlusThirteenNukuAlofa(62)
        }

-- RG Device

saRgDevice   OBJECT IDENTIFIER ::=  { saRg 1 }

saRgDeviceBase   OBJECT IDENTIFIER ::=  { saRgDevice 1 }

saRgDeviceMode OBJECT-TYPE
    SYNTAX INTEGER {
        multiSsid(1),
        cableHome11(2),
                ipv4(3),
                ipv6(4),
                dualstack(5) }
    MAX-ACCESS    read-write
    STATUS        current
    DESCRIPTION
        "Defines the mode of operation for the device.
        This parameter is stored in non-vol and is multiSsid(1) by default.
        Setting this object via SNMP will cause
        the unit to reboot.
                This MIB will be superseded in the config file by TLV202.
                This MIB will read the proper value if set from TLV202.
                This MIB will be superseded by saRgIpMgmtLanMode inbridge(1) or mixed(4).

                multiSsid(1): Default Value. Value supports IPv4RG with multiple SSID
                        configuration and bridge mode via saRgIpMgmtLanMode MIB.
                        Bridge mode is the same as eRouter disabled mode.
                        IPV4RG is the non eRouter behavior that existed before
                        in our router products.
                cableHome11(2): <deprecated>. Mode is not supported for eRouter devices.
                Ipv4(3): eRouter IPv4 only mode
                Ipv6(4): eRouter IPv6 only mode
                Dualstack(5): eRouter IPv4 and IPv6 dualstack
                Note: cableHome11(2) is deprecated."
    DEFVAL { 1 }
    ::= { saRgDeviceBase 1 }


saRgDeviceResetDefaultEnable OBJECT-TYPE
    SYNTAX TruthValue
    MAX-ACCESS read-write
    STATUS current
    DESCRIPTION
        "This object controls the reset to factory default functionality
         of the gateway. This prevents the local user from using the reset
         switch to gain access to the setup pages using the default user
         name and password. The objective is to prevent theft of service
         from a user who reconfigures the device to add users or change
         wireless settings.
         Enable (object set to true):
          1. Momentary press of the Reset Switch (<5 seconds)
             DOCSIS restart of the modem (reboot, no reset to factory
             default values).
          2. Pressing the reset switch for >5 seconds
             Reboots and resets of all values (modem and router) to
             factory default.
         Disable (object set to false):
          1. Momentary press of the Reset Switch (<5 seconds)
             DOCSIS restart of the modem (reboot, no reset to factory
             default values).
          2. Pressing the reset switch for >5 seconds
             Modem reboots and resets only the cable modem settings to
             factory default values. The router settings should remain and
             should not NOT reset to factory default."
    DEFVAL { true }
    ::= { saRgDeviceBase 2 }

saRgDeviceRemoteWebAccessEnable OBJECT-TYPE
    SYNTAX      TruthValue
    MAX-ACCESS  read-write
    STATUS      current
    DESCRIPTION
            "Controls web page access to the WAN IP address on the gateway.
             If DMS is available in the hardware, and saRgDmsBaseWebRedirect
             is set to true, enabling this feature means to enable port
             forwarding for web access to the DMS (to port 80). Note: the
             entry for this does not appear in port forwarding table or on
             the web pages. Example of the rule: WAN_IP:8080->DMS_IP:80.
             This value is stored in non-vol and is false after factory reset.
             This value can be controlled via a setup web page.

             NOTE: This MIB is applicable only for legacy style web pages"
    ::= { saRgDeviceBase 3 }

saRgDeviceRemoteWebAccessPort OBJECT-TYPE
    SYNTAX      InetPortNumber
    MAX-ACCESS  read-write
    STATUS      current
    DESCRIPTION
            "Defines what port to use for the WAN IP address of the gateway
             to be able to access RG web pages.
             This value is to be stored in non-vol and will persist across reboots.
             Only a factory reset would clear it"
    DEFVAL { 8080 }
    ::= { saRgDeviceBase 4 }

saRgDeviceAdminReadOnly OBJECT-TYPE
    SYNTAX INTEGER {
        none(0),
        wan(1)
        }
    MAX-ACCESS    read-write
    STATUS        obsolete
    DESCRIPTION
        "This object can restrict admin right of access to the RG web pages.
         If set to wan(1), admin will be restricted to read-write access
         from the WAN interface."
    DEFVAL { 0 }
    ::= { saRgDeviceBase 5 }

saRgDeviceLanLanIsolation OBJECT-TYPE
    SYNTAX INTEGER {
        disable(0),
        enable(1)
        }
    MAX-ACCESS    read-write
    STATUS        current
    DESCRIPTION
        "This MIB is only available in D3.0 products.
          This MIB does not take effect if the modem is in VLAN mode i.e if saRgIpMgmtLanMode.32=vlan(5).
        Lan-Lan Isolation allows you block IP access between CPEs connected to the Ethernet ports.
        Use this mib in conjunction with saRgDeviceLanWlanIsolation and saRgDot11BssApIsolation.x for
          complete isolation between CPEs connected to the RG.
        This MIB is written to non-vol and set to disable(0) after a factory reset.
        disable(0)- No Isolation
        enable(1)- Enable Isolation feature"
    DEFVAL { 0 }
    ::= { saRgDeviceBase 6 }

saRgDeviceLanWlanIsolation OBJECT-TYPE
    SYNTAX INTEGER {
        disable(0),
        enable(1)
        }
    MAX-ACCESS    read-write
    STATUS        current
    DESCRIPTION
        "This MIB is only available in D3.0 products.
        This MIB does not take effect if the modem is in VLAN mode i.e if saRgIpMgmtLanMode.32=vlan(5).
        Lan-Wlan Isolation allows you block IP access between CPEs connected to the Ethernet port and
        Wireless SSIDs.
        Use this mib in conjunction with saRgDeviceLanLanIsolation and saRgDot11BssApIsolation.x for
          complete isolation between CPEs connected to the RG.
        This MIB is written to non-vol and set to disable(0) after a factory reset.
        disable(0)- No Isolation
        enable(1)- Enable Isolation feature"
    DEFVAL { 0 }
    ::= { saRgDeviceBase 7 }

saRgDeviceIpv6Trans OBJECT-TYPE
    SYNTAX INTEGER {
        disable(0),
        dslite(1)
        }
    MAX-ACCESS    read-only
    STATUS        current
    DESCRIPTION
        "This MIB will control which IPv6 transition technology is enabled on the device.
        After setting this MIB to disable in the config file, IPv4 traffic will pass normally
                through the device. When switched to dslite, the DSLite feature will be enabled.
                If eRouter is in IPv6-only mode, DS Lite will tunnel IPv4 traffic over IPv6 to the AFTR
                address specified either manually or in the DHCPv6 option-64. See saRgDslite MIB tree
                for more details.
        If this setting is changed by the config file, the CM will reboot.
        This MIB is written to non-vol and set to disable(0) after a factory reset.
        disable(0) - No technology is enabled
        enable(1) - DS lite feature is enabled"
    DEFVAL { 0 }
    ::= { saRgDeviceBase 8 }

saRgDeviceIpv6Passthrough OBJECT-TYPE
     SYNTAX INTEGER {
        disable(0),
        enable(1)
        }
    MAX-ACCESS    read-write
    STATUS        current
    DESCRIPTION
        "This MIB controls IPv6 passthrough on the RG and is applicable in bridge and router modes.

          When disabled the RG will function without any IPv6 passthrough

          When IPv6 passthrough is enabled in Bridge Mode the RG will drop all IPv4 traffic

          When IPv6 passthrough is enabled in router mode the RG will operate as normal for IPv4 traffic, but all IPv6 traffic will passthrough

          This MIB requires CM reboot.

          This MIB is written to non-vol and set to disable(0) after a factory reset."

    DEFVAL { 0 }
    ::= { saRgDeviceBase 9 }

saRgDeviceFactoryReset  OBJECT-TYPE
    SYNTAX INTEGER {
                false(0),
        routerAndWifi(1),
        routerOnly(2),
        wifi(3)
        }
        MAX-ACCESS      read-write
        STATUS          current
        DESCRIPTION
        "Set routerAndWifi(1) to restore default settings of both the router and wifi.
                Set routerOnly(2) to restore default settings of the router.
                Set wifi(3) to restore default settings of the wifi.
                Return false(0) when read."
        DEFVAL { 0 }
        ::= { saRgDeviceBase 1002 }

saRgDeviceReset OBJECT-TYPE
    SYNTAX INTEGER {
                false(0),
        routerAndWifi(1),
        routerOnly(2),
        wifi(3)
        }
    MAX-ACCESS  read-write
    STATUS      current
    DESCRIPTION
                "Set routerAndWifi(1) to reboot the router and WiFi.
                Set routerOnly(2) to reboot the router.
                Set wifi(3) to reboot the WiFi.
                Return false(0) when read."
        DEFVAL { 0 }
        ::= { saRgDeviceBase 1003 }

saRgDeviceConfigBackup   OBJECT IDENTIFIER ::=  { saRgDevice 2 }

saRgDevConfBackupServerType OBJECT-TYPE
    SYNTAX InetAddressType
    MAX-ACCESS read-write
    STATUS current
    DESCRIPTION
        ""
    DEFVAL { ipv4 }
    ::= { saRgDeviceConfigBackup 1 }

saRgDevConfBackupServer OBJECT-TYPE
    SYNTAX  InetAddress
    MAX-ACCESS  read-write
    STATUS current
    DESCRIPTION
        "The address of the TFTP server used for RG config download or upload.
         If the TFTP server is unknown, return 0.0.0.0."
    ::= { saRgDeviceConfigBackup 2 }


saRgDevConfBackupFilename OBJECT-TYPE
    SYNTAX      SnmpAdminString (SIZE (0..64))
    MAX-ACCESS  read-write
    STATUS      current
    DESCRIPTION
        "The file name of the config file to be download or upload.
         If unknown, the string '(unknown)' is returned."
    ::= { saRgDeviceConfigBackup 3 }


saRgDevConfBackupOperStatus OBJECT-TYPE
    SYNTAX INTEGER {
        inProgress(1),
        complete(2),
        failed(3),
        other(4)
        }
    MAX-ACCESS  read-only
    STATUS      current
    DESCRIPTION
        "InProgress(1) indicates that a TFTP download or upload is underway,
         Complete(2) indicates that the last download or upload is successful,
         failed(3) indicates that the last attempted download or upload is falied."
    ::= { saRgDeviceConfigBackup 4 }


saRgDevConfBackupAdminStatus OBJECT-TYPE
    SYNTAX INTEGER {
        download(1),
        upload(2)
        }
    MAX-ACCESS  read-write
    STATUS      current
    DESCRIPTION
        "If set to download(1), the device will initiate a
         TFTP RG config file download using remoteProvisionFilename.
         If set to upload(2), the device will initiate a TFTP RG config file
         upload to remoteProvisionServer. The filename will be the same as
         remoteProvisionFilename.
         At initial startup, this object has the default value of
         download(1)."
    ::= { saRgDeviceConfigBackup 5 }


saRgDeviceUserAccess OBJECT IDENTIFIER ::= { saRgDevice 3 }

saRgDevUserLanAccessEnabled OBJECT-TYPE
    SYNTAX TruthValue
    MAX-ACCESS read-write
    STATUS obsolete
    DESCRIPTION
        "Defines whether user level access is allowed to the SET-UP web pages
         from the LAN side.
         This MIB is only available in D20.
         This parameter is stored in non-vol and is true after factory
         reset."
    ::= { saRgDeviceUserAccess 1 }

saRgDevUserAccessDefaultPassword OBJECT-TYPE
    SYNTAX SnmpAdminString
    MAX-ACCESS read-write
    STATUS obsolete
    DESCRIPTION
        "Defines default password for user.
         If user's password matches the default password (meaning user has
         not changed the password), a change password page comes out every
         time a user connects to the web pages.
         If user's password does not match the default password (meaning user
         has changed it) the change password page does not show.
         This parameter is stored in non-vol and is blank by default.
         If the default password is blank in non-vol (after factory
         default for example), it gets populated with this object's value."
    ::= { saRgDeviceUserAccess 2 }

saRgDevUserAccessClearPassword OBJECT-TYPE
    SYNTAX TruthValue
    MAX-ACCESS read-write
    STATUS obsolete
    DESCRIPTION
        "Clears user passwords if set to true (clear=set to default).
         Always returns false when read."
    DEFVAL { false }
    ::= { saRgDeviceUserAccess 3 }

saRgDeviceUserAccessReadPages OBJECT-TYPE
    SYNTAX SaRgWebWizardSetup
    MAX-ACCESS read-only
    STATUS obsolete
    DESCRIPTION
        "Specifies the read access rights for every section of the WebWizard-Setup.
         The value of (1) means read-only, the value of (0) means no-access.
         If a write access to a web page is enabled, read access is also enabled.
         The value of this objects is stored in non-vol.
         Default value after factory reset is 0xffffffff."
    ::= { saRgDeviceUserAccess 4 }

saRgDeviceUserAccessWritePages OBJECT-TYPE
    SYNTAX SaRgWebWizardSetup
    MAX-ACCESS read-only
    STATUS obsolete
    DESCRIPTION
        "Specifies the write access rights for every section of the WebWizard-Setup.
         The value of (1) means read-write, the value of (0) means read-only or no access.
         If a write access to a web page is enabled, read access is also enabled.
         The value of this objects is stored in non-vol.
         Default value after factory reset is 0xffffffff."
    ::= { saRgDeviceUserAccess 5 }

saRgDeviceUserAccessReadPages2 OBJECT-TYPE
    SYNTAX SaRgWebWizardSetup2
    MAX-ACCESS read-only
    STATUS obsolete
    DESCRIPTION
        "Specifies the read access rights for every section of the WebWizard-Setup.
         The value of (1) means read-only, the value of (0) means no-access.
         If a write access to a web page is enabled, read access is also enabled.
         The value of this objects is stored in non-vol.
         Default value after factory reset is 0x0fffffffffffffffffc0.
         This object applies to the new web pages."
    ::= { saRgDeviceUserAccess 6 }

saRgDeviceUserAccessWritePages2 OBJECT-TYPE
    SYNTAX SaRgWebWizardSetup2
    MAX-ACCESS read-only
    STATUS obsolete
    DESCRIPTION
        "Specifies the write access rights for every section of the WebWizard-Setup.
         The value of (1) means read-write, the value of (0) means read-only or no access.
         If a write access to a web page is enabled, read access is also enabled.
         The value of this objects is stored in non-vol.
         Default value after factory reset is 0x0fffffffffffffffffc0.
         This object applies to the new web pages."
    ::= { saRgDeviceUserAccess 7 }

saRgDevUserAccessUsername OBJECT-TYPE
    SYNTAX SnmpAdminString
    MAX-ACCESS read-write
    STATUS obsolete
    DESCRIPTION
        "Defines the username for user.
         This parameter is stored in non-vol and is blank by default."
    ::= { saRgDeviceUserAccess 8 }

SaRgUserChangedFlag ::= TEXTUAL-CONVENTION
    STATUS       current
    DESCRIPTION
        "WebWizard Setup user changed flag sections.
        NOTE: Only Bits from 0-21 are supported for legacy web pages"
    SYNTAX BITS {
        lanParameters(0),
        wanMTU(1),
        wirelessBasic(2),
        wirelessAdvanced(3),
        wirelessSecurity(4),
        wirelessAccessControl(5),
        fixedCPE(6),
        ipMacPortFiltering(7),
        dmzHost(8),
        blockProxy(9),
        blockCookies(10),
        blockJava(11),
        blockActiveX(12),
        blockPopup(13),
        blockFragments(14),
        detectPortScan(15),
        detectFlood(16),
        firewallEvent(17),
        firewallProtection(18),
            ipsecPassthru(19),
            pptpPassthru(20),
            multicastPassthru(21),
        blockAnonymousIpWan(22),
        wanSetup(23),
        remoteMgmt(24),
        l2TP(25)
        }


saRgDeviceConfiguration   OBJECT IDENTIFIER ::=  { saRgDevice 4 }

saRgDeviceConfigFilename OBJECT-TYPE
    SYNTAX SnmpAdminString
    MAX-ACCESS    read-write
    STATUS        current
    DESCRIPTION
        "Configuration filename from DHCP ACK."
    ::= { saRgDeviceConfiguration 1 }

saRgDeviceConfigStatus OBJECT-TYPE
    SYNTAX INTEGER {
        notSpecified(1),
        inProgress(2),
        success(3),
        errorServer(4),
        errorFileNotFound(5),
        errorBadFile(6),
        download(7)
        }
    MAX-ACCESS read-write
    STATUS current
    DESCRIPTION
        "Status of configuration file download.
         - notSpecified(1): DHCP ACK did not contain necessary information
         - inProgress(2): Configuration file is being downloaded
         - success(3): configuration file download completed successfully
         - errorServer(4): TFTP server did not respond
         - errorFileNotFound(5): no file on the server
         - errorBadFile(6): the file is not good, cannot be processed
         - download(7): commands the unit to download configuration file."
    ::= { saRgDeviceConfiguration 2 }

saRgDeviceUserChangedFlag OBJECT-TYPE
    SYNTAX SaRgUserChangedFlag
    MAX-ACCESS read-write
    STATUS current
    DESCRIPTION
       "Specifies which user changed flags are set. The value of (1) means
        that user changed flag value is set; the value of (0) means that
        the user changed flag is not set.
        The user changed flags are stored in non-vol.
        Default value after factory reset is 0x00000000
        NOTE: Legacy style web pages only support bits from 0-21
        "
    ::= { saRgDeviceConfiguration 3 }

saRgDeviceConfigSnmpEnable OBJECT-TYPE
    SYNTAX BITS {
        rgWan(0),
        rgDualIp(1),
                rgLanIp(2),
                rgPortForward(3)
    }
    MAX-ACCESS    read-write
    STATUS        current
    DESCRIPTION
        "Controls SNMP manager status on interfaces. If bit set to 0, the SNMP
         access is disabled. If bit set to 1, the SNMP access is enabled.
                 This MIB only applies to IPv4RG mode and is not relevant in
                 eRouter modes. "
    DEFVAL { '00'h }
    ::= { saRgDeviceConfiguration 4 }

saRgDeviceConfigIgnore  OBJECT-TYPE
    SYNTAX INTEGER {
        require(0),
        notRequire(1),
        notDownload(2)
        }
    MAX-ACCESS  read-only
    STATUS      current
    DESCRIPTION
        "This object controls if RG configuration file is to be downloaded.
         require(0): per specification, if DHCP contains parameters for the
                     file dowload, the RG MUST try to download it.
         notRequire(1): when config file download fails after exponential backoff,
                        RG will not retry DHCP and continue to be operational.
         notDownload(2): RG will not download config file.
         This MIB can be only in CM configuration file."
    DEFVAL { 0 }
    ::= { saRgDeviceConfiguration 5 }


saRgDeviceTimeSetup   OBJECT IDENTIFIER ::=  { saRgDevice 5 }

saRgDeviceTimeSetupNtpEnabled OBJECT-TYPE
    SYNTAX TruthValue
    MAX-ACCESS read-write
    STATUS current
    DESCRIPTION
        "Stored in non-vol, disabled after factory reset."
    ::= { saRgDeviceTimeSetup 1 }

saRgDeviceTimeSetupNtpServerTable OBJECT-TYPE
       SYNTAX      SEQUENCE OF SaRgDeviceTimeSetupNtpServerEntry
       MAX-ACCESS  not-accessible
       STATUS      current
       DESCRIPTION
               "Up to 3 NTP servers are supported. This table
                is stored in non-vol. Default entries after factory
                reset are:
                1: time.nist.gov
                2: nist.aol-ca.truetime.com
                3: nist1-ny.glassey.com"
    ::= { saRgDeviceTimeSetup 2 }

saRgDeviceTimeSetupNtpServerEntry OBJECT-TYPE
    SYNTAX      SaRgDeviceTimeSetupNtpServerEntry
    MAX-ACCESS  not-accessible
    STATUS      current
    DESCRIPTION
            ""
    INDEX { saRgDeviceTimeSetupNtpServerIndex }
    ::= { saRgDeviceTimeSetupNtpServerTable 1 }

SaRgDeviceTimeSetupNtpServerEntry ::= SEQUENCE {
    saRgDeviceTimeSetupNtpServerIndex      INTEGER,
    saRgDeviceTimeSetupNtpServerAddress    SnmpAdminString
    }

saRgDeviceTimeSetupNtpServerIndex OBJECT-TYPE
    SYNTAX      INTEGER (1..3)
    MAX-ACCESS  not-accessible
    STATUS      current
    DESCRIPTION
            "The index"
    ::= { saRgDeviceTimeSetupNtpServerEntry 1 }

saRgDeviceTimeSetupNtpServerAddress OBJECT-TYPE
    SYNTAX      SnmpAdminString
    MAX-ACCESS  read-write
    STATUS      current
    DESCRIPTION
            "IP address or FQDN of the NTP server."
    ::= { saRgDeviceTimeSetupNtpServerEntry 2 }

saRgDeviceTimeSetupZone OBJECT-TYPE
    SYNTAX SaRgTimeZone
    MAX-ACCESS read-write
    STATUS current
    DESCRIPTION
        "Time zone for the gateway.
         Stored in non-vol, gmtZeroDublinEdinburghLisbonLondon(26)
         after factory reset."
    ::= { saRgDeviceTimeSetup 3 }

saRgDeviceTimeSetupDst OBJECT-TYPE
    SYNTAX INTEGER (0..120)
    UNITS "Minutes"
    MAX-ACCESS read-write
    STATUS current
    DESCRIPTION
        "Daylight saving time. If set to 0, DST is disabled
         Stored in non-vol, 0 after factory reset."
    ::= { saRgDeviceTimeSetup 4 }


-- Login control table - obsolete

saRgDeviceLoginControlTable OBJECT-TYPE
       SYNTAX      SEQUENCE OF SaRgDeviceLoginControlEntry
       MAX-ACCESS  not-accessible
       STATUS      obsolete
       DESCRIPTION
               "Rules of accessing Setup RG configuration section by user and operator."
    ::= { saRgDevice 6 }


saRgDeviceLoginControlEntry OBJECT-TYPE
    SYNTAX      SaRgDeviceLoginControlEntry
    MAX-ACCESS  not-accessible
    STATUS      obsolete
    DESCRIPTION
            "List of rules of accessing Setup RG configuration section of WebWizard"
    INDEX { ifIndex, saRgDeviceLoginControlName }
    ::= { saRgDeviceLoginControlTable 1 }

SaRgDeviceLoginControlEntry ::= SEQUENCE {
    saRgDeviceLoginControlName  INTEGER,
    saRgDeviceLoginControlState INTEGER
    }

saRgDeviceLoginControlName OBJECT-TYPE
    SYNTAX INTEGER {
        user(1),
        operator(2)
        }
    MAX-ACCESS  not-accessible
    STATUS      obsolete
    DESCRIPTION
            ""
    ::= { saRgDeviceLoginControlEntry 1 }

saRgDeviceLoginControlState OBJECT-TYPE
    SYNTAX INTEGER  {
        disable(0),
        enable(2)
        }
    MAX-ACCESS  read-only
    STATUS      obsolete
    DESCRIPTION
            "Control user and operator access to Setup RG configuration page per interface."
    ::= { saRgDeviceLoginControlEntry 2 }


-- MIBs to poll IANA / PD info for eRouter interface

saRgDeviceIanaContent   OBJECT IDENTIFIER ::=  { saRgDevice 7 }

saRgDeviceIanaIAID OBJECT-TYPE
        SYNTAX Unsigned32
        MAX-ACCESS read-only
        STATUS current
        DESCRIPTION
                "Returns the IAID value embedded in the IA_NA for the
eRouter's DHCPv6 lease."
        ::= { saRgDeviceIanaContent 1 }

saRgDeviceIanaT1 OBJECT-TYPE
        SYNTAX Integer32
        MAX-ACCESS read-only
        STATUS current
        DESCRIPTION
                "Returns the T1 value embedded in the IA_NA for the eRouter's
DHCPv6 lease."
        ::= { saRgDeviceIanaContent 2 }

saRgDeviceIanaT2 OBJECT-TYPE
        SYNTAX Integer32
        MAX-ACCESS read-only
        STATUS current
        DESCRIPTION
                "Returns the T2 value embedded in the IA_NA for the eRouter's
DHCPv6 lease."
        ::= { saRgDeviceIanaContent 3 }

saRgDeviceIanaTable OBJECT-TYPE
        SYNTAX SEQUENCE OF SaRgDeviceIanaEntry
        MAX-ACCESS not-accessible
        STATUS current
        DESCRIPTION
                "Table of IA Address entries associated with IA_NA for the
eRouter's DHCPv6 lease."
        ::= { saRgDeviceIanaContent 4 }

saRgDeviceIanaEntry OBJECT-TYPE
    SYNTAX      SaRgDeviceIanaEntry
    MAX-ACCESS  not-accessible
    STATUS      current
    DESCRIPTION
            "Table of IA Address entries associated with IA_NA for the
eRouter's DHCPv6 lease."
    INDEX { saRgDeviceIanaIndex }
    ::= { saRgDeviceIanaTable 1 }

SaRgDeviceIanaEntry ::= SEQUENCE {
    saRgDeviceIanaIndex              INTEGER,
    saRgDeviceIanaValue              InetAddress,
    saRgDeviceIanaPreferredLifetime  Integer32,
    saRgDeviceIanaValidLifetime      Integer32
    }

saRgDeviceIanaIndex OBJECT-TYPE
    SYNTAX      INTEGER (1..4)
    MAX-ACCESS  not-accessible
    STATUS      current
    DESCRIPTION
            "The index"
    ::= { saRgDeviceIanaEntry 1 }

saRgDeviceIanaValue OBJECT-TYPE
    SYNTAX      InetAddress
    MAX-ACCESS  read-only
    STATUS      current
    DESCRIPTION
            "IPv6 address provided to the eRouter WAN interface via DHCPv6."
    ::= { saRgDeviceIanaEntry 2 }

saRgDeviceIanaPreferredLifetime OBJECT-TYPE
    SYNTAX      Integer32
    MAX-ACCESS  read-only
    STATUS      current
    DESCRIPTION
            "Preferred Lifetime setting for an IPv6 address assigned to the
eRouter."
    ::= { saRgDeviceIanaEntry 3 }

saRgDeviceIanaValidLifetime OBJECT-TYPE
    SYNTAX      Integer32
    MAX-ACCESS  read-only
    STATUS      current
    DESCRIPTION
            "Valid Lifetime setting for an IPv6 address assigned to the
eRouter."
    ::= { saRgDeviceIanaEntry 4 }



saRgDeviceIapdContent   OBJECT IDENTIFIER ::=  { saRgDevice 8 }

saRgDeviceIapdIAID OBJECT-TYPE
        SYNTAX Unsigned32
        MAX-ACCESS read-only
        STATUS current
        DESCRIPTION
                "Returns the IAID value embedded in the IA_PD for the
eRouter's DHCPv6 lease."
        ::= { saRgDeviceIapdContent 1 }

saRgDeviceIapdT1 OBJECT-TYPE
        SYNTAX Integer32
        MAX-ACCESS read-only
        STATUS current
        DESCRIPTION
                "Returns the T1 value embedded in the IA_PD for the eRouter's
DHCPv6 lease."
        ::= { saRgDeviceIapdContent 2 }

saRgDeviceIapdT2 OBJECT-TYPE
        SYNTAX Integer32
        MAX-ACCESS read-only
        STATUS current
        DESCRIPTION
                "Returns the T2 value embedded in the IA_PD for the eRouter's
DHCPv6 lease."
        ::= { saRgDeviceIapdContent 3 }

saRgDeviceIapdTable OBJECT-TYPE
        SYNTAX SEQUENCE OF SaRgDeviceIapdEntry
        MAX-ACCESS not-accessible
        STATUS current
        DESCRIPTION
                "Table of IA Prefix entries associated with IA_PD for the
eRouter's DHCPv6 lease."
        ::= { saRgDeviceIapdContent 4 }

saRgDeviceIapdEntry OBJECT-TYPE
    SYNTAX      SaRgDeviceIapdEntry
    MAX-ACCESS  not-accessible
    STATUS      current
    DESCRIPTION
            "Table of IA Address entries associated with IA_PD for the
eRouter's DHCPv6 lease."
    INDEX { saRgDeviceIapdIndex }
    ::= { saRgDeviceIapdTable 1 }

SaRgDeviceIapdEntry ::= SEQUENCE {
    saRgDeviceIapdIndex              INTEGER,
    saRgDeviceIapdPreferredLifetime  Integer32,
    saRgDeviceIapdValidLifetime      Integer32,
    saRgDeviceIapdPrefixLength       INTEGER,
    saRgDeviceIapdPrefixValue        InetAddress
    }

saRgDeviceIapdIndex OBJECT-TYPE
    SYNTAX      INTEGER (1..4)
    MAX-ACCESS  not-accessible
    STATUS      current
    DESCRIPTION
            "The index"
    ::= { saRgDeviceIapdEntry 1 }

saRgDeviceIapdPreferredLifetime OBJECT-TYPE
    SYNTAX      Integer32
    MAX-ACCESS  read-only
    STATUS      current
    DESCRIPTION
            "Preferred Lifetime setting for an IPv6 address assigned to the
eRouter."
    ::= { saRgDeviceIapdEntry 2 }

saRgDeviceIapdValidLifetime OBJECT-TYPE
    SYNTAX      Integer32
    MAX-ACCESS  read-only
    STATUS      current
    DESCRIPTION
            "Valid Lifetime setting for an IPv6 address assigned to the
eRouter."
    ::= { saRgDeviceIapdEntry 3 }

saRgDeviceIapdPrefixLength OBJECT-TYPE
        SYNTAX          INTEGER
        MAX-ACCESS      read-only
        STATUS          current
        DESCRIPTION
                "Length (in bits) for this prefix."
        ::= { saRgDeviceIapdEntry 4 }

saRgDeviceIapdPrefixValue OBJECT-TYPE
        SYNTAX          InetAddress
        MAX-ACCESS      read-only
        STATUS          current
        DESCRIPTION
                "Prefix address specified in the IA_PD."
        ::= { saRgDeviceIapdEntry 5 }



-- ******************
-- ***** 802.11 *****
-- ******************

saRgDot11 OBJECT IDENTIFIER ::=  { saRg 2 }


-- *************************
-- GENERAL AND CHANNEL SETUP
-- *************************

saRgDot11MgmtBase OBJECT IDENTIFIER ::= { saRgDot11 1 }

saRgDot11OperMode OBJECT-TYPE
    SYNTAX      INTEGER {
                notAvailable(0),
                off(1),
                remote(2),
                local(3)
    }
    MAX-ACCESS  read-write
    STATUS      current
    DESCRIPTION
        "Used to control the 802.11 operational mode. If set to
         notAvailable(0), then the wireless interface will be disabled, with
         the radio off, and no wireless settings web pages will be available to
         the user.
         If set to off(1) then the wireless interface will be disabled, but
         there may be a web page present which indicates that wireless service
         is available and that the MSO should be contacted to enable it.
         If set to remote(2), then the wireless interface will be enabled, but
         the configuration web pages are read-only so that the user may not
         change the settings.
         If set to local(3), then the wireless interface will be enabled, and
         the web pages will be read-write so that the user has full control over
         the settings.
         This parameter is stored in non-vol and set to local(3) after factory
         reset."
    ::= { saRgDot11MgmtBase 1 }

saRgDot11CurrentChannel OBJECT-TYPE
    SYNTAX      Unsigned32 (0..216)
    MAX-ACCESS  read-write
    STATUS      current
    DESCRIPTION
        "Controls and reflects the current channel number.
         The value of 0 means auto channel selection.
         This parameter is stored in non-vol and is 0
         after factory reset.

         For 802.11b/g/n modes in 2.4 GHz, the available channels are 1-14.
         For 802.11a/n modes in 5 GHz, the available channels are 34-216.
         Channel selection is subjected to restrictions based on Wifi
         Country Code"
    ::= { saRgDot11MgmtBase 3 }

saRgDot11BeaconInterval OBJECT-TYPE
    SYNTAX      Unsigned32  (1..65535)
    UNITS       "milliseconds"
    MAX-ACCESS  read-write
    STATUS      current
    DESCRIPTION
        "Controls and reflects the beacon interval for the device.
         This parameter is stored in non-vol."
    ::= { saRgDot11MgmtBase 4 }

saRgDot11DTIMInterval OBJECT-TYPE
    SYNTAX      Unsigned32  (1..255)
    UNITS       "milliseconds"
    MAX-ACCESS  read-write
    STATUS      current
    DESCRIPTION
        "Controls and reflects the DTIM interval for the device.
         This parameter is stored in non-vol."
    ::= { saRgDot11MgmtBase 5 }

-- Renamed from saRgDot11FragmentationThreshold to avoid conflict w/ IEEE 802.11 MIB
saRgDot11FragThresh OBJECT-TYPE
    SYNTAX      Unsigned32  (256..2346)
    UNITS       "bytes"
    MAX-ACCESS  read-write
    STATUS      current
    DESCRIPTION
        "Controls and reflects the fragmentation threshold for the device.
         This parameter is stored in non-vol."
    ::= { saRgDot11MgmtBase 6 }

-- Renamed from saRgDot11RTSThreshold to avoid conflict w/ IEEE 802.11 MIB
saRgDot11RTSThresh OBJECT-TYPE
    SYNTAX      Unsigned32  (0..2347)
    MAX-ACCESS  read-write
    STATUS      current
    DESCRIPTION
        "Controls and reflects the RTS threshold for the device.
         This parameter is stored in non-vol."
    ::= { saRgDot11MgmtBase 7 }


-- Renamed from saRgDot11ShortRetryLimit to avoid conflict w/ IEEE 802.11 MIB
saRgDot11SRL OBJECT-TYPE
    SYNTAX      Unsigned32  (1..255)
    MAX-ACCESS  read-write
    STATUS      current
    DESCRIPTION
        "Controls and reflects the short retry limit for the device.
         This parameter is stored in non-vol."
    ::= { saRgDot11MgmtBase 8 }

-- Renamed from saRgDot11LongRetryLimit to avoid conflict w/ IEEE 802.11 MIB
saRgDot11LRL OBJECT-TYPE
    SYNTAX      Unsigned32  (1..255)
    MAX-ACCESS  read-write
    STATUS      current
    DESCRIPTION
        "Controls and reflects the long retry limit for the device.
         This parameter is stored in non-vol."
    ::= { saRgDot11MgmtBase 9 }

saRgDot1154gNetMode OBJECT-TYPE
    SYNTAX INTEGER {
        only11g(4),
        maxCompatibility(5)
        }
    MAX-ACCESS  read-write
    STATUS      obsolete
    DESCRIPTION
        "Controls and reflects the behavior of the device with regards to which
         flavor of 802.11 is used.  If set to maxCompatibility(5), the device
         will interoperate with the widest variety of 54g and 802.11b clients.
         If set to only11g(4), only 54g clients will be accepted.
         Note that this MIB should be enabled only in 2.4GHz.

         This parameter is stored in non-vol and is set to maxCompatibility(5)
         after factory reset."
    ::= { saRgDot11MgmtBase 10 }

saRgDot1154gProtectionEnable OBJECT-TYPE
    SYNTAX      TruthValue
    MAX-ACCESS  read-write
    STATUS      current
    DESCRIPTION
        "Controls and reflects the state of 54g protection.  If set to true(1),
         the AP will use RTS/CTS to improve 802.11g performance in mixed
         802.11g/802.11b networks.  Set to false(2) to maximize 802.11g
         throughput under most conditions.
         Note that this MIB should be enabled only in 2.4GHz.
         This parameter is stored in non-vol."
    ::= { saRgDot11MgmtBase 11 }

saRgDot11Rate OBJECT-TYPE
    SYNTAX      INTEGER {
                auto(0),
                mbits1(1),
                mbits2(2),
                mbits5-5(5),
                mbits6(6),
                mbits9(9),
                mbits11(11),
                mbits12(12),
                mbits18(18),
                mbits24(24),
                mbits36(36),
                mbits48(48),
                mbits54(54)
    }
    MAX-ACCESS  read-write
    STATUS      current
    DESCRIPTION
        "Forces the transmission rate for the AP to a particular speed.
         Note that the 802.11b rates, including mbits1(1), mbits2(2),
         mbits5-5(5), and mbits11(11), are not available in 5GHz.
         This parameter is stored in non-vol."
    ::= { saRgDot11MgmtBase 12 }

saRgDot11OutputPower OBJECT-TYPE
    SYNTAX      INTEGER {
                percent25(25),
                percent50(50),
                percent75(75),
                percent100(100)
    }
    MAX-ACCESS  read-write
    STATUS      current
    DESCRIPTION
        "Sets the output power relative to the hardware's maximum capability.
         This parameter is stored in non-vol."
    ::= { saRgDot11MgmtBase 13 }

saRgDot11Country OBJECT-TYPE
    SYNTAX      INTEGER {
                worldWide(0),
                thailand(1),
                israel(2),
                jordan(3),
                china(4),
                japan(5),
                usa(6),
                europe(7),
                allChannels(8)
    }
    MAX-ACCESS  read-write
    STATUS      current
    DESCRIPTION
        "Restricts the channel set based on country requirements.
         This parameter is stored in non-vol and is worldWide(0)
         (channels 1-11) after factory reset.
         
         The MIB does not function for BRCM based Cisco release starting 5.5.10
         
         "
    ::= { saRgDot11MgmtBase 14 }

saRgDot11Antenna OBJECT-TYPE
    SYNTAX  INTEGER {
        disableIntTx(0),
        enableIntTx(1)
        }
    MAX-ACCESS  read-write
    STATUS      current
    DESCRIPTION
        "This parameter is stored in non-vol and set to
         disableIntTx(0) after factory reset."
    ::= { saRgDot11MgmtBase 15 }

saRgDot11MbssUserControl OBJECT-TYPE
    SYNTAX INTEGER (1..8|65536..16711680)
    MAX-ACCESS read-write
    STATUS current
    DESCRIPTION
        "Sets the number of user controlled Wifi networks via web pages.
         1: The user has control over the primary wireless network only.
            No guest network page is displayed.
         2: The user has control over the primary wireless network and
            one guest network. No drop down menu (or only 1 item in the
            menu) for additional guest network configuration.
         3: Same as above with 2 guest networks.
         4: Same as above with 3 guest networks.
         5: Same as above with 4 guest networks.
             6: Same as above with 5 guest networks.
             7: Same as above with 6 guest networks.
         8: Same as above with 7 guest networks.

         Bit Mask Control:
         Bit 16: -- User has control over Primary Wireless Network               :  65536
         Bit 17: -- User has control over Guest Network 1 (interface 33) : 131072
         Bit 18: -- User has control over Guest Network 2 (interface 34) : 262144
         Bit 19: -- User has control over Guest Network 3 (interface 35) : 524288
         Bit 20: -- User has control over Guest Network 4 (interface 36) :1048576
         Bit 21: -- User has control over Guest Network 5 (interface 37) :2097152
         Bit 22: -- User has control over Guest Network 6 (interface 38) :4194304
         Bit 23: -- User has control over Guest Network 7 (interface 39) :8388608

         This object value is stored in non-vol and set to 1
         after factory reset."
    ::= { saRgDot11MgmtBase 16 }

saRgDot11MbssUseNonvol OBJECT-TYPE
    SYNTAX TruthValue
    MAX-ACCESS read-write
    STATUS current
    DESCRIPTION
        "Allows to save additional BSS parameters to non-vol if set to true.
         Primary BSS parameters are ALWAYS stored in non-vol.
         This object value is stored in non-vol and set to false
         after factory reset."
    ::= { saRgDot11MgmtBase 17 }

saRgDot11MbssAdminControl OBJECT-TYPE
    SYNTAX INTEGER (1..8|65536..16711680)
    MAX-ACCESS read-write
    STATUS current
    DESCRIPTION
        "Sets the number of admin controlled Wifi networks via web pages.
         1: The admin has control over the primary wireless network only.
            No guest network page is displayed.
         2: The admin has control over the primary wireless network and
            one guest network. No drop down menu (or only 1 item in the
            menu) for additional guest network configuration.
         3: Same as above with 2 guest networks.
         4: Same as above with 3 guest networks.
         5: Same as above with 4 guest networks.
             6: Same as above with 5 guest networks.
             7: Same as above with 6 guest networks.
         8: Same as above with 7 guest networks.

         Bit 16: -- Admin Has control over Primary Wireless Network               :  65536
         Bit 17: -- Admin Has control over Guest Network 1 (interface 33) : 131072
         Bit 18: -- Admin Has control over Guest Network 2 (interface 34) : 262144
         Bit 19: -- Admin Has control over Guest Network 3 (interface 35) : 524288
         Bit 20: -- Admin Has control over Guest Network 4 (interface 36) :1048576
         Bit 21: -- Admin Has control over Guest Network 5 (interface 37) :2097152
         Bit 22: -- Admin Has control over Guest Network 6 (interface 38) :4194304
         Bit 23: -- Admin Has control over Guest Network 7 (interface 39) :8388608

         This object value is stored in non-vol and set to 1
         after factory reset."

    ::= { saRgDot11MgmtBase 18 }

saRgDot11ActualChannel OBJECT-TYPE
    SYNTAX      INTEGER
    MAX-ACCESS  read-only
    STATUS      current
    DESCRIPTION
        "Reports the current channel number that wireless is on.
         The value of 0 means wireless is disabled."
    ::= { saRgDot11MgmtBase 19 }

saRgDot11OnOffPushButtonTime OBJECT-TYPE
    SYNTAX      INTEGER (0..11)
    UNITS       "seconds"
    MAX-ACCESS  read-write
    STATUS      current
    DESCRIPTION
        "Specifies how long to press WPS button to enable or disable
         the WiFi interface (primary SSID). When set to 11, the feature
         is disabled.
         Stored in non-vol, 11 after factory reset."
    ::= { saRgDot11MgmtBase 20 }

saRgDot11Wmm OBJECT-TYPE
    SYNTAX  INTEGER {
        disable(0),
        enable(1)
        }
    MAX-ACCESS  read-write
    STATUS      current
    DESCRIPTION
        "Mib to Enable/Disable Wifi-Multi Media (WMM) QOS fetures.
        This parameter is stored in non-vol and set to
        enable(1) after a factory reset."
    DEFVAL { 1 }
    ::= { saRgDot11MgmtBase 21 }

 saRgDot11WmmNoAck OBJECT-TYPE
    SYNTAX  INTEGER {
        disable(0),
        enable(1)
        }
    MAX-ACCESS  read-write
    STATUS      current
    DESCRIPTION
        "Mib to control whether Wifi packets require acknowledgement.
        disable(0) Use acknowledgemnet for Wifi packets.
        enable(1)  Sets No acknowledgement which allows for higher throughput and lower latency when some
                   packetloss is acceptable (ex. VoIP).
        Note: If WMM is disabled then this setting has no effect, and you can Not disable Acks from being
        returned from the stations.
        This parameter is stored in non-vol and set to disable(0) after a factory reset."
    DEFVAL { 0 }
    ::= { saRgDot11MgmtBase 22 }

 saRgDot11MulticastRate OBJECT-TYPE
    SYNTAX      INTEGER {
                                disable(0),
                mbits1(1),
                mbits2(2),
                mbits5-5(5),
                mbits6(6),
                mbits9(9),
                mbits11(11),
                mbits12(12),
                mbits18(18),
                mbits24(24),
                mbits36(36),
                mbits48(48),
                mbits54(54)
        }
    UNITS       "Mbps"
    MAX-ACCESS  read-write
    STATUS      current
    DESCRIPTION
        "Forces the dot11 multicast Phy transmission rate.
         Note that the 802.11b rates, including mbits1(1), mbits2(2),
         mbits5-5(5), and mbits11(11), are not available in 5GHz.
         This object is stored in non-vol and defaults to disable(0) after factory reset."
    DEFVAL { 0 }
    ::= { saRgDot11MgmtBase 23 }

saRgDot11WirelessButtonOperation OBJECT-TYPE
    SYNTAX  INTEGER {
        disable(0),
        enable(1)
    }
    MAX-ACCESS    read-write
    STATUS        current
    DESCRIPTION
        "To enable or disable the button press of wireless ON/OFF button.
                  This feature will work only on products that has the wireless ON/OFF button.
                  This MIB will control if the Wireless ON/OFF button can be pressed or not.
                  If it¿s enable then button press would take effect otherwise there will not be any effect on button press.
                  By default value will be set to enable(1)."
    DEFVAL { 1 }
    ::= { saRgDot11MgmtBase 24 }

saRgDot11ChannelSelectionPolicy OBJECT-TYPE
    SYNTAX  INTEGER {
        default(0),
        legacy(1),
                intf(2),
                intfbusy(3),
                optimized(4)
    }
    MAX-ACCESS    read-write
    STATUS        current
    DESCRIPTION
        "Mib to select Auto Channel Selection policy.
                default(0): By default the number of APs and the Composite Noise Score is used to decide the best channel available to the radio.
        legacy(1): Only considers number of APs.
                intf(2): Only considers number of APs and interference measurement.
                intfbusy(3): Considers interference and channel occupancy (including number of APs).
                optimized(4): Considers interference (including back ground noise), channel occupancy (including number of APs) and Tx power.
                This parameter is stored in non-vol and set to default(0) after a factory reset."
    DEFVAL { 0 }
    ::= { saRgDot11MgmtBase 25 }
-- =====================
-- WiFi Scan results
-- =====================

saRgDot11ApsScan OBJECT IDENTIFIER ::= { saRgDot11MgmtBase 26 }

saRgDot11ApsScanEnable OBJECT-TYPE
    SYNTAX      TruthValue
    MAX-ACCESS  read-write
    STATUS      current
    DESCRIPTION
        "If set to true(1), WiFi Radio will be configured to scan for the APs.
        Scan results with list of neighboring APs will be updated in saRgDot11ApsScanResultsTable.
        Always returns false(2) when read."
    ::= { saRgDot11ApsScan 1 }


saRgDot11ApsScanResultsTable  OBJECT-TYPE
    SYNTAX      SEQUENCE OF SaRgDot11ApsScanResultsEntry
    MAX-ACCESS  not-accessible
    STATUS      current
    DESCRIPTION
        "A table of neighboring APs list found after APs Scan request (saRgDot11ApsScan).
        The table can list up to 32 number of APs."
    ::= { saRgDot11ApsScan 2 }

saRgDot11ApsScanResultsEntry OBJECT-TYPE
    SYNTAX      SaRgDot11ApsScanResultsEntry
    MAX-ACCESS  not-accessible
    STATUS      current
    DESCRIPTION
        "An entry describing neighboring AP information. First element wifiValid
        determines if the current entry is valid or not. The information includes
        SSID, RSSI, Channel, Mac Address etc."
    INDEX   { ifIndex }
    ::= { saRgDot11ApsScanResultsTable 1  }

SaRgDot11ApsScanResultsEntry ::=
    SEQUENCE    {
        saRgDot11ApsScanValid           INTEGER,
        saRgDot11ApsScanNetworkName     OCTET STRING,
        saRgDot11ApsScanSecurityMode    OCTET STRING,
        saRgDot11ApsScanPhyMode         OCTET STRING,
        saRgDot11ApsScanRssi            INTEGER,
        saRgDot11ApsScanChannel         INTEGER,
        saRgDot11ApsScanMacAddress      PhysAddress
    }

saRgDot11ApsScanValid OBJECT-TYPE
    SYNTAX      INTEGER {
                invalid(0),
                valid(1)
    }
    MAX-ACCESS  read-only
    STATUS      current
    DESCRIPTION
        "Determines if the current entry is valid or not."
    ::= { saRgDot11ApsScanResultsEntry 1 }

saRgDot11ApsScanNetworkName OBJECT-TYPE
    SYNTAX      OCTET STRING
    MAX-ACCESS  read-only
    STATUS      current
    DESCRIPTION
        "Neighboring AP name or SSID."
    ::= { saRgDot11ApsScanResultsEntry 2 }

saRgDot11ApsScanSecurityMode OBJECT-TYPE
    SYNTAX      OCTET STRING
    MAX-ACCESS  read-only
    STATUS      current
    DESCRIPTION
        "Neighboring AP security mode."
    ::= { saRgDot11ApsScanResultsEntry 3 }

saRgDot11ApsScanPhyMode OBJECT-TYPE
    SYNTAX      OCTET STRING
    MAX-ACCESS  read-only
    STATUS      current
    DESCRIPTION
        "Neighboring AP PHY mode."
    ::= { saRgDot11ApsScanResultsEntry 4 }

saRgDot11ApsScanRssi OBJECT-TYPE
    SYNTAX      INTEGER
    MAX-ACCESS  read-only
    STATUS      current
    DESCRIPTION
        "Neighboring AP receive signal strenth."
    ::= { saRgDot11ApsScanResultsEntry 5 }

saRgDot11ApsScanChannel OBJECT-TYPE
    SYNTAX      INTEGER
    MAX-ACCESS  read-only
    STATUS      current
    DESCRIPTION
        "Neighboring AP operating channel."
    ::= { saRgDot11ApsScanResultsEntry 6 }

saRgDot11ApsScanMacAddress OBJECT-TYPE
    SYNTAX      PhysAddress
    MAX-ACCESS  read-only
    STATUS      current
    DESCRIPTION
        "Neighboring AP MAC address."
    ::= { saRgDot11ApsScanResultsEntry 7 }

-- =====================
-- PER BSS CONFIGURATION
-- =====================
-- The interface numbers are:
-- 32: SSID1 + LAN
-- 33: SSID2
-- 34: SSID3
-- 35: SSID4
-- 36: SSID5
-- 37: SSID6
-- 38: SSID7
-- 39: SSID8


saRgDot11Bss OBJECT IDENTIFIER ::= { saRgDot11 2 }


saRgDot11BssTable  OBJECT-TYPE
    SYNTAX      SEQUENCE OF SaRgDot11BssEntry
    MAX-ACCESS  not-accessible
    STATUS      current
    DESCRIPTION
        "BSS table"
    ::= { saRgDot11Bss 1 }

saRgDot11BssEntry OBJECT-TYPE
    SYNTAX      SaRgDot11BssEntry
    MAX-ACCESS  not-accessible
    STATUS      current
    DESCRIPTION
        "A row in the table which represents parameters for SSID."
    INDEX   { ifIndex }
    ::= { saRgDot11BssTable 1 }

SaRgDot11BssEntry ::=
    SEQUENCE {
        saRgDot11BssId            PhysAddress,
        saRgDot11BssEnable        INTEGER,
        saRgDot11BssSsid          OCTET STRING,
        saRgDot11BssSecurityMode  INTEGER,
        saRgDot11BssClosedNetwork TruthValue,
        saRgDot11BssAccessMode    INTEGER,
        saRgDot11BssLanAccess     INTEGER,
        saRgDot11BssDsBwReserve   INTEGER,
        saRgDot11BssDsBwPriority  INTEGER,
        saRgDot11BssMaxNumSta     INTEGER,
        saRgDot11BssCountStaAsCpe TruthValue,
        saRgDot11BssUserStatus    INTEGER,
        saRgDot11BssHotSpot       TruthValue,
        saRgDot11BssApIsolation   INTEGER,
        saRgDot11BssSecSsidTrafficPriority  INTEGER,
        saRgDot11BssRejectPriSsidSta        TruthValue,
		saRgDot11BssRejectPriSsidStaCount	TruthValue
        }

saRgDot11BssId OBJECT-TYPE
    SYNTAX      PhysAddress
    MAX-ACCESS  read-only
    STATUS      current
    DESCRIPTION
        "Returns the BSSID"
    ::= { saRgDot11BssEntry 1 }

saRgDot11BssEnable OBJECT-TYPE
    SYNTAX INTEGER {
        enable(1),
        disable(2),
        enableOnline(3)
        }
    MAX-ACCESS  read-write
    STATUS      current
    DESCRIPTION
        "Controls the BSS state.
         When set to enableOnline(3), the SSID is enabled only
         when the cable modem is online. When the modem changes
         state to offline, the AP will send dissasociation messages
         to the STAs connected to the SSID and then disable.
         The value of primary BSS is stored in non-vol and is enabled(1)
         after factory reset.
         The other BSSs are disabled by default. If other
         BSS's SSID name is not defined, the BSS will not
         be enabled."
    ::= { saRgDot11BssEntry 2 }

saRgDot11BssSsid OBJECT-TYPE
    SYNTAX      OCTET STRING (SIZE(0..32))
    MAX-ACCESS  read-write
    STATUS      current
    DESCRIPTION
        "Controls and reflects the service set identifier.
         The value of primary BSS is stored in non-vol and is
         empty after factory reset.
         If other BSS's SSID name is not defined, the BSS
         will not be enabled."
    ::= { saRgDot11BssEntry 3 }

saRgDot11BssSecurityMode OBJECT-TYPE
    SYNTAX INTEGER {
        disabled(0),
        wep(1),
        wpaPsk(2),
        wpa2Psk(3),
        wpaEnterprise(4),
        wpa2Enterprise(5),
        --radiusWep(6)
        wpaWpa2Psk(7),
        wpaWpa2Enterprise(8)
        }
    MAX-ACCESS  read-write
    STATUS      current
    DESCRIPTION
        "Secrity for BSS.
         Beacause WPA2 is backwords compatible with WPA, setting this
         object to wpaWpa2Psk(7) is allowed and has the same effect as
         setting to wpa2Psk(3). The same is true for wpaWpa2Enterprise(8)
         and wpa2Enterprise(5).
         The value for primary BSS is stored in non-vol and is wpaWpa2Psk(7)
         after factory reset.
         For each other BSS security has to be included in configuration
         file or the BSS will be disabled."
    ::= { saRgDot11BssEntry 4 }

saRgDot11BssClosedNetwork OBJECT-TYPE
    SYNTAX      TruthValue
    MAX-ACCESS  read-write
    STATUS      current
    DESCRIPTION
        "Controls whether the device will operate in closed network mode.  If
         set to true(1), then the network mode is closed and the SSID will not
         be broadcast in beacon packets.  If set to false(2), then the network
         mode is open and the SSID will be broadcast in beacon packets.
         The value for primary BSS is stored in non-vol.
         The default value for other BSSs is false."
    ::= { saRgDot11BssEntry 5 }

saRgDot11BssAccessMode OBJECT-TYPE
    SYNTAX      INTEGER {
                allowAny(0),
                allowList(1),
                denyList(2)
    }
    MAX-ACCESS  read-write
    STATUS      current
    DESCRIPTION
        "Controls what stations will be given access to the device.  If set to
         allowAny(0), then any station will be allowed to connect.  If set
         to allowList(1), then only stations whose MAC address appears in
         the saRgDot11AccessMacTable will be allowed to connect.
         The value for primary BSS is stored in non-vol.
         The default value for other BSSs is 0."
    ::= { saRgDot11BssEntry 6 }

-- not implemented
saRgDot11BssLanAccess OBJECT-TYPE
    SYNTAX INTEGER {
        lan(1),
        guest(2)
        }
    MAX-ACCESS read-write
    STATUS current
    DESCRIPTION
        "If set to lan(1), this service set will be authorized as a member of
         the local area network.  If set to guest(2), this service set will
         have access to the wide area internet, but will have restricted access
         to the local area network.
         Default values are lan(1) for the primary BSS and guest(2) for other BSSs.
         NOTE: NOT IMPLEMENTED"
    ::= { saRgDot11BssEntry 8 }

saRgDot11BssDsBwReserve OBJECT-TYPE
    SYNTAX INTEGER
    UNITS "Bps"
    MAX-ACCESS  read-write
    STATUS      current
    DESCRIPTION
        "Controls the downstream (from AP to client) throughput
         in Bytes per second from AP to client on a BSS.
         This object reserves the throughput for a BSS. The rest of
         leftover bandwidth is assigned based on BSS priority.
         Note: if the reserved bandwidth is not used, it is shared
         with other BSSs based on their priority.
         If set to 0 there is no reservation.

         Example:
         BSS 1, 2 and 3 have reservation of 3Mb/s each. BSS 1 is higher priority
         than 2, which is higher than 3.
         - only BSS 3 transmits full bandwidth traffic: BSS 3 gets full bandwidth
         - BSS 2 starts transmitting at 2 Mb/s: BSS 2 gets 2 Mb/s, BSS 3 gets
           full-2 Mb/s
         - BSS 2 increases to 4 Mb/s: BSS 3 gets full-4 Mb/s, BSS 2 gets 4 Mb/s
         - BSS 2 increases to full: BSS 3 gets 3 Mb/s, BSS 2 gets full-3 Mb/s
         - BSS 1 starts transmitting at 2 Mb/s: BSS 3 gets 3 mbps, BSS 2 gets
           full-5 Mb/s, BSS 1 gets 2 Mb/s
         - BSS 1 increases to full: BSS 3 gets 3 Mb/s, BSS 2 gets 3 Mb/s, BSS 1
           gets full-6 Mb/s
           NOTE: NOT IMPLEMENTED"
    DEFVAL { 0 }
    ::= { saRgDot11BssEntry 9 }

saRgDot11BssDsBwPriority OBJECT-TYPE
    SYNTAX INTEGER (1..4)
    MAX-ACCESS  read-write
    STATUS      current
    DESCRIPTION
        "Sets the priority for non-reserved bandwidth. 1 is the highest priority.
         If BSSs use the same priority, they get bandwidth based on contention.
         NOTE: NOT IMPLEMENTED"
    DEFVAL { 4 }
    ::= { saRgDot11BssEntry 10 }

saRgDot11BssMaxNumSta OBJECT-TYPE
    SYNTAX INTEGER (1..128)
    MAX-ACCESS read-write
    STATUS current
    DESCRIPTION
        "This object defines the maximum number of STAs that can connect to
         this SSID. Note that the maximum number of STA accross all SSIDs in
         the AP is 128.
         Default value is 128 for all SSIDs.
         The value for primary BSS is stored in non-vol."
    ::= { saRgDot11BssEntry 11 }

saRgDot11BssCountStaAsCpe OBJECT-TYPE
    SYNTAX TruthValue
    MAX-ACCESS read-only
    STATUS current
    DESCRIPTION
        "STAs in Max-Count of CPEs (Max number of CPE in CM config file),
         default per eDOCSIS spec.
         This setting is used to control counting STAs in Max-Count of CPEs.
         false: Do not count STAs as a CPE
         true: Count STAs as a CPE
         This object applies when the BSS is in bridge mode. In router mode
         the STAs are behind the NAT and do not count towards max-CPE anyway.
         Note: applies only to secondary BSSs."
    DEFVAL { true }
    ::= { saRgDot11BssEntry 12 }

saRgDot11BssUserStatus OBJECT-TYPE
    SYNTAX INTEGER {
        enable(1),
        disable(2)
        }
    MAX-ACCESS  read-only
    STATUS      current
    DESCRIPTION
        "Provides the BSS Id Web UI or Wireless ON/OFF (if exist) status that
                  is set by the user. If the user can press the Wireless ON/OFF (if
                  exist) button and it¿s status can be seen in BSS ID Web UI. If user
                  changes access point status in Web UI, it will reflect the status of
                  Wireless ON/OFF LED."
    ::= { saRgDot11BssEntry 13 }

saRgDot11BssHotSpot OBJECT-TYPE
    SYNTAX TruthValue
    MAX-ACCESS read-write
    STATUS current
    DESCRIPTION
        "Determines/Sets whether this BSS is a HotSpot BSS.  This allows the MSO to
                 specify which BSS is configured for Hotspot Operation.
         Note: applies only to Guest BSSs (non primary)."
    DEFVAL { false }
    ::= { saRgDot11BssEntry 14 }


saRgDot11BssApIsolation OBJECT-TYPE
    SYNTAX INTEGER {
        disable(0),
        enable(1)
        }
    MAX-ACCESS  read-write
    STATUS      current
    DESCRIPTION
        "This MIB is only available in D3.0 products.
        AP Isolation (Access Point Isolation) allows you to isloate traffic between CPEs on
        the same Wifi SSID. This allows a measure of security to prevent hackers from accessing other CPEs in
        a public Wifi environment.
        Ex. When this MIB is enabled you can not ping between CPEs connected to the same SSID.
        AP Isolation is settable per SSID in either VLAN or non VLAN modes.
        This MIB is written to non-vol and set to disable(0) after a factory reset.
        disable(0)- No AP Isolation
        enable(1)- Enable AP Isolation feature."
    DEFVAL { 0 }
    ::= { saRgDot11BssEntry 15 }

saRgDot11BssSecSsidTrafficPriority OBJECT-TYPE
    SYNTAX INTEGER {
        disable(0),
        acBk(1)
        }
    MAX-ACCESS  read-only
    STATUS      current
    DESCRIPTION
        "This MIB is only available in D3.0 products and applicable for secondary SSID in hotspot
        environment. When disabled, all the traffic to the secondary SSID in question would have same WMM QoS
        parameters as the primary SSID. When set to ac_bk(1), the secondary SSID traffic would be classified as
        AC_BK resulting in better DS prioritization for primary SSID traffic"

    DEFVAL { 0 }
    ::= { saRgDot11BssEntry 16 }

saRgDot11BssRejectPriSsidSta OBJECT-TYPE
    SYNTAX TruthValue
    MAX-ACCESS  read-only
    STATUS      current
    DESCRIPTION
        "This MIB is only available in D3.0 products and applicable for secondary SSID in hotspot
        environment. By default, a private SSID STA can associate to hotspot SSID. This MIB can be used
        to reject private SSID STAs to associate with hotspot SSID if and only if STA has associated with private
        SSID once before."

    DEFVAL { false }
    ::= { saRgDot11BssEntry 17 }
	
saRgDot11BssRejectPriSsidStaCount OBJECT-TYPE
      SYNTAX INTEGER {
		disable(0),
        enable(1)
        }
      MAX-ACCESS read-write
      STATUS      current
    DESCRIPTION
        "This MIB is only available in D3.0 products and applicable for secondary SSID in hotspot
        environment.This MIB should be used in conjunction with saRgDot11BssRejectPriSsidSta. When both enable it is
        possible for the STA to connect for one time to the secondary SSID instead of zero times when only 
        saRgDot11BssRejectPriSsidSta is enable"

    DEFVAL { 0 }
    ::= { saRgDot11BssEntry 18 }

-- RESTRICT ACCESS WITH MAC TABLE

saRgDot11AccessMacTable  OBJECT-TYPE
    SYNTAX      SEQUENCE OF SaRgDot11AccessMacEntry
    MAX-ACCESS  not-accessible
    STATUS      current
    DESCRIPTION
        "A table of MAC addresses which represents stations that will be allowed
         to connect to the device if saRgDot11AccessMode is set to
         restrictToList(1)."
    ::= { saRgDot11Bss 2 }

saRgDot11AccessMacEntry OBJECT-TYPE
    SYNTAX      SaRgDot11AccessMacEntry
    MAX-ACCESS  not-accessible
    STATUS      current
    DESCRIPTION
        "A row in the table that specifies a single station MAC address."
    INDEX   { ifIndex, saRgDot11AccessMacIndex }
    ::= { saRgDot11AccessMacTable 1 }

SaRgDot11AccessMacEntry ::=
    SEQUENCE    {
                saRgDot11AccessMacIndex       INTEGER,
                saRgDot11AccessMacStation     MacAddress,
                saRgDot11BssAccessStatus      RowStatus
    }

saRgDot11AccessMacIndex OBJECT-TYPE
    SYNTAX      INTEGER (1..32)
    MAX-ACCESS  not-accessible
    STATUS      current
    DESCRIPTION
        "Indicates the instance of this table row."
    ::= { saRgDot11AccessMacEntry 1 }

saRgDot11AccessMacStation OBJECT-TYPE
    SYNTAX      MacAddress
    MAX-ACCESS  read-create
    STATUS      current
    DESCRIPTION
        "A MAC address of a station which will be allowed to connect to the
         device if saRgDot11AccessMode is set to restrictToList(1)."
    ::= { saRgDot11AccessMacEntry 2 }

saRgDot11BssAccessStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         dot11BssAccessStatus column is 'notReady'.

         In particular, a newly created row cannot be made active until the
         corresponding instance of dot11BssAccessStation has been set.

         Only rows with a status of active(1) will be applied."
    ::= { saRgDot11AccessMacEntry 3 }

-- PRIMARY BSS SPECIFIC

saRgDot11BssPrimary OBJECT IDENTIFIER ::= { saRgDot11Bss 3 }

saRgDot11BssPrimarySsidType OBJECT-TYPE
    SYNTAX INTEGER {
        mac6char(1),
        mac6char-prefix(2),
        mac4char-prefix(3),
        prefix-force(4)
        -- Value 5 is reserved
        }
    MAX-ACCESS  read-write
    STATUS      current
    DESCRIPTION
        "This object specifies the type of SSID used.
         mac6char(1): If saRgDot11BssSsid.32 is empty, the SSID is the last
                      3 bytes of DOCSIS MAC address, displayed as 6 lowercase
                      hex characters.
                      If saRgDot11BssSsid.32 is not empty, SSID is the value from
                      saRgDot11BssSsid.32 (set by SNMP or the user).
         mac6char-prefix(2): the same as mac6char(2) with the prefix addition
                             defined in saRgDot11BssPrimarySsidPrefix.
                             If  saRgDot11BssSsid.32 is not empty, this prefix
                             does not show.
         mac4char-prefix(3): the same as mac6char-prefix(2) but 4 MAC characters
                             instead of 6.
         prefix-force(4): The prefix is always included, even if saRgDot11BssSsid.32
                          is empty.
         Note: stored in non-vol. mac6char(1) after factory reset"
    ::= { saRgDot11BssPrimary 1 }

saRgDot11BssPrimarySsidPrefix OBJECT-TYPE
    SYNTAX SnmpAdminString (SIZE(1..16))
    MAX-ACCESS  read-write
    STATUS      current
    DESCRIPTION
        "The prefix for primary SSID, if saRgDot11BssSsid.32 is empty
         and saRgDot11BssPrimarySsidType is set to mac6char-prefix(2).
         Stored in non-vol. Empty after factory reset."
    ::= { saRgDot11BssPrimary 2 }

saRgDot11BssPrimarySsidSuffix OBJECT-TYPE
	SYNTAX INTEGER {
	    disable(0),
		suffix2-4(1),
		suffix5(2),
		suffixboth(3)
		}
	MAX-ACCESS read-write
	STATUS 	   current
	DESCRIPTION
		"The suffix for primary SSID. Default no suffix is added. 
		suffix2-4(1): -2.4Ghz will be added as suffix for the 2.4G band
		suffix5(2): -5Ghz will be added as suffix for the 5G band
		suffixboth(3): Both -2.4Ghz and -5Ghz will be added as suffix to the corresponding frequency band.
		 "  
    DEFVAL { 0 }
	::= { saRgDot11BssPrimary 3 }

-- RESTRICT ACCESS WITH HOTSPOT MAC TABLE

saRgDot11AccessHotspotMacTable  OBJECT-TYPE
    SYNTAX      SEQUENCE OF SaRgDot11AccessHotspotMacEntry
    MAX-ACCESS  not-accessible
    STATUS      current
    DESCRIPTION
        "A table of MAC addresses which represents stations that will be allowed
         to connect to the device if saRgDot11AccessMode is set to
         restrictToList(1)."
    ::= { saRgDot11Bss 4 }

saRgDot11AccessHotspotMacEntry OBJECT-TYPE
    SYNTAX      SaRgDot11AccessHotspotMacEntry
    MAX-ACCESS  not-accessible
    STATUS      current
    DESCRIPTION
        "A row in the table that specifies a single station MAC address."
    INDEX   { ifIndex, saRgDot11AccessHotspotMacIndex }
    ::= { saRgDot11AccessHotspotMacTable 1 }

SaRgDot11AccessHotspotMacEntry ::=
    SEQUENCE    {
                saRgDot11AccessHotspotMacIndex       INTEGER,
                saRgDot11AccessHotspotMacStation     MacAddress,
                saRgDot11BssAccessHotspotStatus      RowStatus
    }

saRgDot11AccessHotspotMacIndex OBJECT-TYPE
    SYNTAX      INTEGER (1..32)
    MAX-ACCESS  not-accessible
    STATUS      current
    DESCRIPTION
        "Indicates the instance of this table row."
    ::= { saRgDot11AccessHotspotMacEntry 1 }

saRgDot11AccessHotspotMacStation OBJECT-TYPE
    SYNTAX      MacAddress
    MAX-ACCESS  read-create
    STATUS      current
    DESCRIPTION
        "A MAC address of a station which will be allowed to connect to the
         device if saRgDot11AccessMode is set to restrictToList(1)."
    ::= { saRgDot11AccessHotspotMacEntry 2 }

saRgDot11BssAccessHotspotStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         dot11BssAccessStatus column is 'notReady'.

         In particular, a newly created row cannot be made active until the
         corresponding instance of dot11BssAccessStation has been set.

         Only rows with a status of active(1) will be applied."
    ::= { saRgDot11AccessHotspotMacEntry 3 }
	
-- ******************
-- PRIVACY PARAMETERS
-- ******************

-- saRgDot11MgmtPrivacy contains objects from the 'Privacy' web page

saRgDot11Privacy OBJECT IDENTIFIER ::= { saRgDot11 3 }


-- WPA

saRgDot11WpaTable  OBJECT-TYPE
    SYNTAX      SEQUENCE OF SaRgDot11WpaEntry
    MAX-ACCESS  not-accessible
    STATUS      current
    DESCRIPTION
        "WPA table"
    ::= { saRgDot11Privacy 1 }

saRgDot11WpaEntry OBJECT-TYPE
    SYNTAX      SaRgDot11WpaEntry
    MAX-ACCESS  not-accessible
    STATUS      current
    DESCRIPTION
        "A row in the table which represents WPA parameters for BSS."
    INDEX   { ifIndex }
    ::= { saRgDot11WpaTable 1 }

SaRgDot11WpaEntry ::=
    SEQUENCE    {
        saRgDot11WpaAlgorithm          INTEGER,
        saRgDot11WpaPreSharedKey       OCTET STRING,
        saRgDot11WpaGroupRekeyInterval INTEGER
    }

saRgDot11WpaAlgorithm OBJECT-TYPE
    SYNTAX INTEGER {
        tkip(0),
        aes(1),
        tkipPlusAes(2)
        }
    MAX-ACCESS  read-write
    STATUS      current
    DESCRIPTION
        "The value of tkip(0) is not allowed when security is WPA2.
         The value for primary BSS is stored in non-vol and tkipPlusAes(2)
         after factory reset.
         The default value for other BSSs is tkip."
    ::= { saRgDot11WpaEntry 1 }

saRgDot11WpaPreSharedKey OBJECT-TYPE
    SYNTAX      OCTET STRING (SIZE(8..64))
    MAX-ACCESS  read-write
    STATUS      current
    DESCRIPTION
        "Sets the WPA Pre-Shared Key (PSK).  This value MUST be either a
         64-digit hexadecimal number, OR a 8 to 63 character ASCII string.
         The value for primary BSS is stored in non-vol and is the serial
         number of the device after factory reset.
         The default value for other BSSs is 8 0's.
         This object return an empty string when read."
    ::= { saRgDot11WpaEntry 2 }

saRgDot11WpaGroupRekeyInterval OBJECT-TYPE
    SYNTAX      INTEGER
    UNITS       "seconds"
    MAX-ACCESS  read-write
    STATUS      current
    DESCRIPTION
        "Sets the WPA Group Rekey Interval in seconds. Set to zero to disable
         periodic rekeying.
         The value for primary BSS is stored in non-vol and is 3600 after
         factory reset.
         The default value for other BSSs is 3600."
    ::= { saRgDot11WpaEntry 3 }


-- RADIUS

saRgDot11RadiusTable  OBJECT-TYPE
    SYNTAX      SEQUENCE OF SaRgDot11RadiusEntry
    MAX-ACCESS  not-accessible
    STATUS      current
    DESCRIPTION
        "WPA table"
    ::= { saRgDot11Privacy 2 }

saRgDot11RadiusEntry OBJECT-TYPE
    SYNTAX      SaRgDot11RadiusEntry
    MAX-ACCESS  not-accessible
    STATUS      current
    DESCRIPTION
        "A row in the table which represents WPA parameters for BSS."
    INDEX   { ifIndex }
    ::= { saRgDot11RadiusTable 1 }

SaRgDot11RadiusEntry ::=
    SEQUENCE    {
        saRgDot11RadiusAddressType    InetAddressType,
        saRgDot11RadiusAddress        InetAddress,
        saRgDot11RadiusPort           InetPortNumber,
        saRgDot11RadiusKey            DisplayString,
        saRgDot11RadiusReAuthInterval INTEGER
    }


saRgDot11RadiusAddressType OBJECT-TYPE
    SYNTAX      InetAddressType
    MAX-ACCESS  read-write
    STATUS      current
    DESCRIPTION
            "Type of RADIUS server IP address."
    DEFVAL { ipv4 }
    ::= { saRgDot11RadiusEntry 1 }


saRgDot11RadiusAddress OBJECT-TYPE
    SYNTAX      InetAddress
    MAX-ACCESS  read-write
    STATUS      current
    DESCRIPTION
        "Sets RADIUS server IP address.
         The value for primary BSS is stored in non-vol and is 0.0.0.0
         after factory reset.
         The default value for other BSSs is 0.0.0.0."
    ::= { saRgDot11RadiusEntry 2 }

saRgDot11RadiusPort OBJECT-TYPE
    SYNTAX      InetPortNumber
    MAX-ACCESS  read-write
    STATUS      current
    DESCRIPTION
        "Sets the UDP port used to communicate with the RADIUS server.
         The value for primary BSS is stored in non-vol and is 1645
         after factory reset.
         The default value for other BSSs is 1645."
    ::= { saRgDot11RadiusEntry 3 }

saRgDot11RadiusKey OBJECT-TYPE
    SYNTAX      DisplayString
    MAX-ACCESS  read-write
    STATUS      current
    DESCRIPTION
        "Sets or displays the RADIUS key.
         The value for primary BSS is stored in non-vol and is null
         after factory reset.
         The default value for other BSSs is null.
         This object return an empty string when read."
    ::= { saRgDot11RadiusEntry 4 }

saRgDot11RadiusReAuthInterval OBJECT-TYPE
    SYNTAX      INTEGER
    UNITS       "seconds"
    MAX-ACCESS  read-write
    STATUS      current
    DESCRIPTION
        "Sets the RADIUS Rekey Interval in seconds.
         Set to zero to disable periodic rekeying.
         The value for primary BSS is stored in non-vol and is 3600
         after factory reset.
         The default value for other BSSs is 3600."
    ::= { saRgDot11RadiusEntry 5 }


-- WEP

saRgDot11WepTable  OBJECT-TYPE
    SYNTAX      SEQUENCE OF SaRgDot11WepEntry
    MAX-ACCESS  not-accessible
    STATUS      current
    DESCRIPTION
        "WEP table"
    ::= { saRgDot11Privacy 3 }

saRgDot11WepEntry OBJECT-TYPE
    SYNTAX      SaRgDot11WepEntry
    MAX-ACCESS  not-accessible
    STATUS      current
    DESCRIPTION
        "A row in the table which represents WPA parameters for BSS."
    INDEX   { ifIndex }
    ::= { saRgDot11WepTable 1 }

SaRgDot11WepEntry ::=
    SEQUENCE {
        saRgDot11WepDefaultKey      INTEGER,
        saRgDot11WepEncryptionMode  INTEGER,
        saRgDot11WepPassPhrase      OCTET STRING
    }

saRgDot11WepDefaultKey OBJECT-TYPE
    SYNTAX      INTEGER (1..4)
    MAX-ACCESS  read-write
    STATUS      current
    DESCRIPTION
        "Controls and reflects the default key which will be used when 64 or
         128 bit encryption is enabled.  Indicates the entry from the
         saRgDot1164BitKeyTable if saRgDot11EncryptionMode is set to wep64(1), or
         the entry from the saRgDot11128BitKeyTable if saRgDot11EncryptionMode is set
         to wep128(2).
         The value for primary BSS is stored in non-vol and is 1 after factory reset.
         The default value for other BSSs is 1."
    ::= { saRgDot11WepEntry 1 }

saRgDot11WepEncryptionMode OBJECT-TYPE
    SYNTAX INTEGER {
        wep64(0),
        wep128(1)
        }
    MAX-ACCESS  read-write
    STATUS      current
    DESCRIPTION
         "The value for primary BSS is stored in non-vol and is wep128(1)
          after factory reset.
          The default value for other BSSs is wep128."
    ::= { saRgDot11WepEntry 2 }

saRgDot11WepPassPhrase OBJECT-TYPE
    SYNTAX      DisplayString (SIZE(0..32))
    MAX-ACCESS  read-write
    STATUS      current
    DESCRIPTION
        "Controls and reflects the WEP pass phrase.
         The value for primary BSS is stored in non-vol and is null
         after factory reset.
         The default value for other BSSs is null.
         This object return an empty string when read."
    ::= { saRgDot11WepEntry 3 }



-- WEP 64-bit keys:

saRgDot11Wep64BitKeyTable  OBJECT-TYPE
    SYNTAX      SEQUENCE OF SaRgDot11Wep64BitKeyEntry
    MAX-ACCESS  not-accessible
    STATUS      current
    DESCRIPTION
        "A table of 40 bit key values used when saRgDot11WepEncryptionMode
         is set to wep64(0)."
    ::= { saRgDot11Privacy 4 }

saRgDot11Wep64BitKeyEntry OBJECT-TYPE
    SYNTAX      SaRgDot11Wep64BitKeyEntry
    MAX-ACCESS  not-accessible
    STATUS      current
    DESCRIPTION
        "A row in the table which represents a single 64 bit key."
    INDEX   { ifIndex, saRgDot11Wep64BitKeyIndex }
    ::= { saRgDot11Wep64BitKeyTable 1 }

SaRgDot11Wep64BitKeyEntry ::=
    SEQUENCE    {
                saRgDot11Wep64BitKeyIndex       Integer32,
                saRgDot11Wep64BitKeyValue       OCTET STRING
    }

saRgDot11Wep64BitKeyIndex OBJECT-TYPE
    SYNTAX      Integer32 (1..4)
    MAX-ACCESS  not-accessible
    STATUS      current
    DESCRIPTION
        "Identifies the instance of this table row."
    ::= { saRgDot11Wep64BitKeyEntry 1 }

saRgDot11Wep64BitKeyValue OBJECT-TYPE
    SYNTAX      OCTET STRING (SIZE(5))
    MAX-ACCESS  read-write
    STATUS      current
    DESCRIPTION
        "A 40 bit key to be used when saRgDot11WepEncryptionMode is set to wep64(1).
         The value for primary BSS is stored in non-vol and is all 1's after factory
         reset.
         The default value for other BSSs is all 0's.
         This object return an empty string when read."
    ::= { saRgDot11Wep64BitKeyEntry 2 }

-- WEP 128-bit keys:

saRgDot11Wep128BitKeyTable  OBJECT-TYPE
    SYNTAX      SEQUENCE OF SaRgDot11Wep128BitKeyEntry
    MAX-ACCESS  not-accessible
    STATUS      current
    DESCRIPTION
        "A table of 104 bit key values used when saRgDot11WepEncryptionMode
         is set to wep128(1)."
    ::= { saRgDot11Privacy 5 }

saRgDot11Wep128BitKeyEntry OBJECT-TYPE
    SYNTAX      SaRgDot11Wep128BitKeyEntry
    MAX-ACCESS  not-accessible
    STATUS      current
    DESCRIPTION
        "A row in the table which represents a single 128 bit key."
    INDEX   { ifIndex, saRgDot11Wep128BitKeyIndex }
    ::= { saRgDot11Wep128BitKeyTable 1 }

SaRgDot11Wep128BitKeyEntry ::=
    SEQUENCE    {
                saRgDot11Wep128BitKeyIndex       Integer32,
                saRgDot11Wep128BitKeyValue       OCTET STRING
    }

saRgDot11Wep128BitKeyIndex OBJECT-TYPE
    SYNTAX      Integer32 (1..4)
    MAX-ACCESS  not-accessible
    STATUS      current
    DESCRIPTION
        "Identifies the instance of this table row."
    ::= { saRgDot11Wep128BitKeyEntry 1 }

saRgDot11Wep128BitKeyValue OBJECT-TYPE
    SYNTAX      OCTET STRING (SIZE(13))
    MAX-ACCESS  read-write
    STATUS      current
    DESCRIPTION
        "A 104 bit key to be used when saRgDot11WepEncryptionMode is set to wep128(2).
         The value for primary BSS is stored in non-vol and is all 1's.
         The default value for other BSSs is all 0's.
         This object return an empty string when read."
    ::= { saRgDot11Wep128BitKeyEntry 2 }


saRgDot11PrivacyWps OBJECT IDENTIFIER ::= { saRgDot11Privacy 6 }

saRgDot11PrivacyWpsPushButtonTime OBJECT-TYPE
    SYNTAX      INTEGER (0..10)
    UNITS       "seconds"
    MAX-ACCESS  read-write
    STATUS      current
    DESCRIPTION
        "Specifies how long to press WPS button to start the WPS
         procedure. 0 means disable WPS.
         Stored in non-vol, 1 after factory reset."
    ::= { saRgDot11PrivacyWps 1 }


-- ASSOCIATED CLIENTS TREE

saRgDot11Client OBJECT IDENTIFIER ::=  { saRgDot11 4 }

saRgDot11ClientBase OBJECT IDENTIFIER ::=  { saRgDot11Client 1 }

saRgDot11ClientTable  OBJECT-TYPE
    SYNTAX      SEQUENCE OF SaRgDot11ClientEntry
    MAX-ACCESS  not-accessible
    STATUS      current
    DESCRIPTION
        "A table of wireless clients that are associated with the BSS."
    ::= { saRgDot11Client 2 }

saRgDot11ClientEntry OBJECT-TYPE
    SYNTAX      SaRgDot11ClientEntry
    MAX-ACCESS  not-accessible
    STATUS      current
    DESCRIPTION
        "A row in the table that specifies a single station MAC address."
    INDEX   { ifIndex, saRgDot11ClientIndex }
    ::= { saRgDot11ClientTable 1 }

SaRgDot11ClientEntry ::=
    SEQUENCE    {
                saRgDot11ClientIndex       Integer32,
                saRgDot11ClientStation     MacAddress,
				saRgDot11ClientConnectMode INTEGER
    }

saRgDot11ClientIndex OBJECT-TYPE
    SYNTAX      Integer32
    MAX-ACCESS  not-accessible
    STATUS      current
    DESCRIPTION
        "Indicates the instance of this table row."
    ::= { saRgDot11ClientEntry 1 }

saRgDot11ClientStation OBJECT-TYPE
    SYNTAX      MacAddress
    MAX-ACCESS  read-only
    STATUS      current
    DESCRIPTION
        "A MAC address of a client associated with the BSS."
    ::= { saRgDot11ClientEntry 2 }

saRgDot11ClientConnectMode OBJECT-TYPE
	SYNTAX INTEGER {
	    disable(0),
		a(1),
		g(2),
		n(3)
		}
	MAX-ACCESS read-only
	STATUS 	   current
	DESCRIPTION
		"This MIB will query WiFi client info. If no info found, return disable(0). When information is found, return connect mode a(1),g(2),or n(3)."  
    DEFVAL { 0 }
	::= { saRgDot11ClientEntry 3 }


--  802.11n settings

saRgDot11n OBJECT IDENTIFIER ::= { saRgDot11 5 }

saRgdot11nMode OBJECT-TYPE
    SYNTAX INTEGER {
        auto(1),
        off(2),
        n-only(3),
        b-mode(16),
        g-mode(32),
        bg-mode(48),
        a-mode(64),
        n-only(128),
        gn-mode(160),
        bgn-mode(176),
        an-mode(192),
        ac-only(256),
        nac-only(384),
        anac-mode(448)
        }

    MAX-ACCESS  read-write
    STATUS      current
    DESCRIPTION
        "Determines which 802.11 mode the radio will run in.
         This object must be set by either the legacy or bitmask method.

         In legacy method,
         auto(1)  : supports all the 802.11 modes available in the radio.
         off(2)   : supports the legacy mode only (11b/g in 2.4GHz and 11a in 5GHz).
         n-only(3): accepts 11n-capable clients only but supports all the modes available in the radio.

         In bitmask method,
         b-mode(16)    : supports 11b mode in 2.4GHz.
         g-mode(32)    : supports 11g mode in 2.4GHz.
         bg-mode(48)   : supports 11b/g mode in 2.4GHz (16+32).
         a-mode(64)    : supports 11a mode in 5GHz.
         n-only(128)   : accepts 11n-capable clients only but supports both legacy and 11n modes in 2.4GHz or 5GHz.
         gn-mode(160)  : supports 11g/n mode in 2.4GHz (32+128).
         bgn-mode(176) : supports all 11b/g/n modes in 2.4GHz (16+32+128).
         an-mode(192)  : supports 11a/n modes in 5GHz (64+128).
         ac-only(256)  : accepts 11ac-capable clients only but supports 11a/n/ac modes in 5GHz.
         nac-only(384) : accepts 11n-capable clients only but supports 11a/n/ac modes in 5GHz (128+256).
         anac-mode(448): supports all 11a/n/ac modes in 5GHz (64+128+256).

         Note: Some options may not be available depending on the radio model.
         Note: The change of this object value will also affect other MIB selections, including saRgdot11nExtBandWidth.
         This object is stored in non-vol and defaults to auto(1) after factory reset."
    ::= { saRgDot11n 1 }

saRgdot11nPhyRate OBJECT-TYPE
    SYNTAX INTEGER {
        auto(0),
        legacy(1),
        mbits6-5or13-5(2),
        mbits13or27(3),
        mbits19-5or40-5(4),
        mbits26or54(5),
        mbits39or81(6),
        mbits52or108(7),
        mbits58-5or121-5(8),
        mbits65or135(9),
        reserved1(10),
        reserved2(11),
        reserved3(12),
        reserved4(13),
        mbits78or162(14),
        mbits104or216(15),
        mbits117or243(16),
        mbits130or270(17)
        }
    MAX-ACCESS  read-write
    STATUS      current
    DESCRIPTION
        "Forces the N Phy transmission rate for the AP to a particular speed.  Each pair of rates
         corresponds to a 20 MHz or 40 MHz channel configuration.
         This object is stored in non-vol and defaults to auto(0) after factory reset."
    DEFVAL { auto }
    ::= { saRgDot11n 2 }


saRgdot11nBand OBJECT-TYPE
    SYNTAX INTEGER {
        band-2-4G(1),
        band-5G(2)
        }
    MAX-ACCESS  read-write
    STATUS      current
    DESCRIPTION
        "Determines which Band that we will be operating in. Either the 2.4G or the 5G Hz.
         Note: This is for N cards only.
         This object is stored in non-vol and defaults to band-2-4G(1) after factory reset."
    ::= { saRgDot11n 3 }

saRgdot11nBandWidth OBJECT-TYPE
    SYNTAX INTEGER {
        width-20MHz(1),
        width-40MHz(2),
        width-80MHz(3)
        }
    MAX-ACCESS  read-write
    STATUS      current
    DESCRIPTION
        "Determines which Band Width that we will be operating in. Either the 20MHz or the 40MHz.
         Note: This is for N cards only, and this also affect other MIB selections such as saRgdot11nSideBand.
         The 80 MHz channel width is only applicable for 802.11ac capable cards. If a user sets this to 80 MHz, SNMPset would fail for non-802.11ac cards
         This object is stored in non-vol and defaults to ? after factory reset."
    ::= { saRgDot11n 4 }

saRgdot11nSideBand OBJECT-TYPE
    SYNTAX INTEGER {
        upper(1),
        lower(2)
        }
    MAX-ACCESS  read-write
    STATUS      current
    DESCRIPTION
        "Determines which side Band the channel will operate in.
         Note: This is for N cards only, this mib is dependent of what saRgdot11nBandWidth is selected and only
         applies when 40MHz is selected.
         This object is stored in non-vol and defaults to lower(2) after factory reset."
    ::= { saRgDot11n 5 }

saRgdot11nProtection OBJECT-TYPE
    SYNTAX INTEGER {
        auto(1),
        off(2)
        }
    MAX-ACCESS  read-write
    STATUS      current
    DESCRIPTION
        "Determines if protection will be turned on or off for N mode.
         Note: This is for N cards only.
         This object is stored in non-vol and defaults to auto(1) after factory reset."
    ::= { saRgDot11n 6 }

saRgdot11nObssCoex OBJECT-TYPE
        SYNTAX INTEGER {
                disable(0),
                enable(1)
                }
        MAX-ACCESS read-write
        STATUS     current
        DESCRIPTION
                "Allows MSO to control OBSS (Overlapping BSS) Coexistance parameter for 802.11n 40MHz channel width.
                 By default it is enabled and is stored in non-vol
                 Factory reset would clear it and would be enable(1) after factory reset.
                 When disabled, the 802.11n Wifi would stay in 40 MHz channel-width inspite of interference from other
                 wifi channels. While enabled, 802.11n would coexist with 802.11g channels using 20 MHz default channel-width
                 "
        ::= { saRgDot11n 7 }

saRgdot11nMulticastRate OBJECT-TYPE
    SYNTAX INTEGER {
        disable(0),
        legacy(1),
        mbits6-5or13-5(2),
        mbits13or27(3),
        mbits19-5or40-5(4),
        mbits26or54(5),
        mbits39or81(6),
        mbits52or108(7),
        mbits58-5or121-5(8),
        mbits65or135(9),
        reserved1(10),
        reserved2(11),
        reserved3(12),
        reserved4(13),
        mbits78or162(14),
        mbits104or216(15),
        mbits117or243(16),
        mbits130or270(17)
        }
    MAX-ACCESS  read-write
    STATUS      current
    DESCRIPTION
        "Forces the dot11n Multicast Phy transmission rate.  Legacy mode forces the rate to be set
                 by dot11MulticastRate.
         This object is stored in non-vol and defaults to disable(0) after factory reset."
    DEFVAL { 0 }
    ::= { saRgDot11n 8 }


----------------------------------------------------------------------
---  saRgDot11ExtMgmt
---  Table to support Multiple Radios
---  Note: Indexes may be set to support specific hardware interfaces.
---  Index 32 MUST match saRgDot11OperMode and vice versa
-----------------------------------------------------------------------

saRgDot11ExtMgmt OBJECT IDENTIFIER ::= { saRgDot11 6 }

saRgDot11ExtMgmtTable  OBJECT-TYPE
    SYNTAX      SEQUENCE OF SaRgDot11ExtMgmtEntry
    MAX-ACCESS  not-accessible
    STATUS      current
    DESCRIPTION
        "Multiple Radio Configuration Table"
    ::= { saRgDot11ExtMgmt 1 }

saRgDot11ExtMgmtEntry OBJECT-TYPE
    SYNTAX      SaRgDot11ExtMgmtEntry
    MAX-ACCESS  not-accessible
    STATUS      current
    DESCRIPTION
        "A row in the table which represents parameters for a Radio.
                 Index 32 should be set for Radio 0 -- 2.4 GHz if populated.
                 Index 112 should be set for Radio 1"

    INDEX   { ifIndex }
    ::= { saRgDot11ExtMgmtTable 1 }

SaRgDot11ExtMgmtEntry ::=
    SEQUENCE {
                saRgDot11ExtOperMode                INTEGER,
                saRgDot11ExtCurrentChannel          Unsigned32,
                saRgDot11ExtBeaconInterval          Unsigned32,
                saRgDot11ExtDTIMInterval            Unsigned32,
                saRgDot11ExtFragThresh              Unsigned32,
                saRgDot11ExtRTSThresh               Unsigned32,
                saRgDot11ExtSRL                     Unsigned32,
                saRgDot11ExtLRL                     Unsigned32,
                saRgDot11ExtCtsProtectionEnable     TruthValue,
                saRgDot11ExtRate                    INTEGER,
                saRgDot11ExtOutputPower             INTEGER,
                saRgDot11ExtCountry                 INTEGER,
                saRgDot11ExtAntenna                 INTEGER,
                saRgDot11ExtMbssUserControl         INTEGER,
                saRgDot11ExtMbssUseNonvol           TruthValue,
                saRgDot11ExtMbssAdminControl        INTEGER,
                saRgDot11ExtActualChannel           INTEGER,
                saRgDot11ExtOnOffPushButtonTime     INTEGER,
                saRgDot11ExtWmm                     INTEGER,
                saRgDot11ExtWmmNoAck                INTEGER,
                saRgDot11ExtMulticastRate           INTEGER,
                saRgDot11ExtWirelessButtonOperation INTEGER
        }

saRgDot11ExtOperMode OBJECT-TYPE
    SYNTAX      INTEGER {
                notAvailable(0),
                off(1),
                remote(2),
                local(3)
    }
    MAX-ACCESS  read-write
    STATUS      current
    DESCRIPTION
        "Used to control the 802.11 operational mode. If set to
         notAvailable(0), then the wireless interface will be disabled, with
         the radio off, and no wireless settings web pages will be available to
         the user.
         If set to off(1) then the wireless interface will be disabled, but
         there may be a web page present which indicates that wireless service
         is available and that the MSO should be contacted to enable it.
         If set to remote(2), then the wireless interface will be enabled, but
         the configuration web pages are read-only so that the user may not
         change the settings.
         If set to local(3), then the wireless interface will be enabled, and
         the web pages will be read-write so that the user has full control over
         the settings.
         This parameter is stored in non-vol and set to local(3) after factory
         reset."
    ::= { saRgDot11ExtMgmtEntry 1 }

saRgDot11ExtCurrentChannel OBJECT-TYPE
    SYNTAX      Unsigned32 (0..216)
    MAX-ACCESS  read-write
    STATUS      current
    DESCRIPTION
        "Controls and reflects the current channel number.
         The value of 0 means auto channel selection.
         This parameter is stored in non-vol and is 0
         after factory reset.

         For 802.11b/g/n modes in 2.4 GHz, the available channels are 1-14.
         For 802.11a/n modes in 5 GHz, the available channels are 34-216.
         Channel selection is subjected to restrictions based on Wifi
         Country Code
         The MIB does not function for BRCM based Cisco release starting 5.5.10"
    ::= { saRgDot11ExtMgmtEntry 3 }

saRgDot11ExtBeaconInterval OBJECT-TYPE
    SYNTAX      Unsigned32  (1..65535)
    UNITS       "milliseconds"
    MAX-ACCESS  read-write
    STATUS      current
    DESCRIPTION
        "Controls and reflects the beacon interval for the device.
         This parameter is stored in non-vol."
    ::= { saRgDot11ExtMgmtEntry 4 }

saRgDot11ExtDTIMInterval OBJECT-TYPE
    SYNTAX      Unsigned32  (1..255)
    UNITS       "milliseconds"
    MAX-ACCESS  read-write
    STATUS      current
    DESCRIPTION
        "Controls and reflects the DTIM interval for the device.
         This parameter is stored in non-vol."
    ::= { saRgDot11ExtMgmtEntry 5 }

-- Renamed from saRgDot11FragmentationThreshold to avoid conflict w/ IEEE 802.11 MIB
saRgDot11ExtFragThresh OBJECT-TYPE
    SYNTAX      Unsigned32  (256..2346)
    UNITS       "bytes"
    MAX-ACCESS  read-write
    STATUS      current
    DESCRIPTION
        "Controls and reflects the fragmentation threshold for the device.
         This parameter is stored in non-vol."
    ::= { saRgDot11ExtMgmtEntry 6 }

-- Renamed from saRgDot11RTSThreshold to avoid conflict w/ IEEE 802.11 MIB
saRgDot11ExtRTSThresh OBJECT-TYPE
    SYNTAX      Unsigned32  (0..2347)
    MAX-ACCESS  read-write
    STATUS      current
    DESCRIPTION
        "Controls and reflects the RTS threshold for the device.
         This parameter is stored in non-vol."
    ::= { saRgDot11ExtMgmtEntry 7 }


-- Renamed from saRgDot11ShortRetryLimit to avoid conflict w/ IEEE 802.11 MIB
saRgDot11ExtSRL OBJECT-TYPE
    SYNTAX      Unsigned32  (1..255)
    MAX-ACCESS  read-write
    STATUS      current
    DESCRIPTION
        "Controls and reflects the short retry limit for the device.
         This parameter is stored in non-vol."
    ::= { saRgDot11ExtMgmtEntry 8 }

-- Renamed from saRgDot11LongRetryLimit to avoid conflict w/ IEEE 802.11 MIB
saRgDot11ExtLRL OBJECT-TYPE
    SYNTAX      Unsigned32  (1..255)
    MAX-ACCESS  read-write
    STATUS      current
    DESCRIPTION
        "Controls and reflects the long retry limit for the device.
         This parameter is stored in non-vol."
    ::= { saRgDot11ExtMgmtEntry 9 }

saRgDot11ExtCtsProtectionEnable OBJECT-TYPE
    SYNTAX      TruthValue
    MAX-ACCESS  read-write
    STATUS      current
    DESCRIPTION
        "Controls and reflects the state of CTS protection.
         If set to true(1), the AP will use RTS/CTS to improve 802.11
         performance in mixed 802.11 networks. Set to false(2) to
         maximize 802.11 throughput under most conditions.
         This parameter is stored in non-vol."
    ::= { saRgDot11ExtMgmtEntry 10 }

saRgDot11ExtRate OBJECT-TYPE
    SYNTAX      INTEGER {
                auto(0),
                mbits1(1),
                mbits2(2),
                mbits5-5(5),
                mbits6(6),
                mbits9(9),
                mbits11(11),
                mbits12(12),
                mbits18(18),
                mbits24(24),
                mbits36(36),
                mbits48(48),
                mbits54(54)
    }
    MAX-ACCESS  read-write
    STATUS      current
    DESCRIPTION
        "Forces the transmission rate for the AP to a particular speed.
         Note that the 802.11b rates, including mbits1(1), mbits2(2),
         mbits5-5(5), and mbits11(11), are not available in 5GHz.
         This parameter is stored in non-vol."
    ::= { saRgDot11ExtMgmtEntry 11 }

saRgDot11ExtOutputPower OBJECT-TYPE
    SYNTAX      INTEGER {
                percent25(25),
                percent50(50),
                percent75(75),
                percent100(100)
    }
    MAX-ACCESS  read-write
    STATUS      current
    DESCRIPTION
        "Sets the output power relative to the hardware's maximum capability.
         This parameter is stored in non-vol."
    ::= { saRgDot11ExtMgmtEntry 12 }

saRgDot11ExtCountry OBJECT-TYPE
    SYNTAX      INTEGER {
                worldWide(0),
                thailand(1),
                israel(2),
                jordan(3),
                china(4),
                japan(5),
                usa(6),
                europe(7),
                allChannels(8)
    }
    MAX-ACCESS  read-write
    STATUS      current
    DESCRIPTION
        "Restricts the channel set based on country requirements.
         This parameter is stored in non-vol and is worldWide(0)
         (channels 1-11) after factory reset."
    ::= { saRgDot11ExtMgmtEntry 13 }

saRgDot11ExtAntenna OBJECT-TYPE
    SYNTAX  INTEGER {
        disableIntTx(0),
        enableIntTx(1)
        }
    MAX-ACCESS  read-write
    STATUS      current
    DESCRIPTION
        "This parameter is stored in non-vol and set to
         disableIntTx(0) after factory reset."
    ::= { saRgDot11ExtMgmtEntry 14 }

saRgDot11ExtMbssUserControl OBJECT-TYPE
    SYNTAX INTEGER (1..8|65536..16711680)
    MAX-ACCESS read-write
    STATUS current
    DESCRIPTION
        "Sets the number of user controlled Wifi networks via web pages.
         1: The user has control over the primary wireless network only.
            No guest network page is displayed.
         2: The user has control over the primary wireless network and
            one guest network. No drop down menu (or only 1 item in the
            menu) for additional guest network configuration.
         3: Same as above with 2 guest networks.
         4: Same as above with 3 guest networks.
         5: Same as above with 4 guest networks.
             6: Same as above with 5 guest networks.
             7: Same as above with 6 guest networks.
         8: Same as above with 7 guest networks.

         Bit Mask Control:
         Bit 16: -- User has control over Primary Wireless Network       :  65536
         Bit 17: -- User has control over Guest Network 1 (interface 33) : 131072
         Bit 18: -- User has control over Guest Network 2 (interface 34) : 262144
         Bit 19: -- User has control over Guest Network 3 (interface 35) : 524288
         Bit 20: -- User has control over Guest Network 4 (interface 36) :1048576
         Bit 21: -- User has control over Guest Network 5 (interface 37) :2097152
         Bit 22: -- User has control over Guest Network 6 (interface 38) :4194304
         Bit 23: -- User has control over Guest Network 7 (interface 39) :8388608

         This object value is stored in non-vol and set to 1
         after factory reset."
    ::= { saRgDot11ExtMgmtEntry 15 }

saRgDot11ExtMbssUseNonvol OBJECT-TYPE
    SYNTAX TruthValue
    MAX-ACCESS read-write
    STATUS current
    DESCRIPTION
        "Allows to save additional BSS parameters to non-vol if set to true.
         Primary BSS parameters are ALWAYS stored in non-vol.
         This object value is stored in non-vol and set to false
         after factory reset."
    ::= { saRgDot11ExtMgmtEntry 16 }

saRgDot11ExtMbssAdminControl OBJECT-TYPE
    SYNTAX INTEGER (1..8|65536..16711680)
    MAX-ACCESS read-write
    STATUS current
    DESCRIPTION
        "Sets the number of admin controlled Wifi networks via web pages.
         1: The admin has control over the primary wireless network only.
            No guest network page is displayed.
         2: The admin has control over the primary wireless network and
            one guest network. No drop down menu (or only 1 item in the
            menu) for additional guest network configuration.
         3: Same as above with 2 guest networks.
         4: Same as above with 3 guest networks.
         5: Same as above with 4 guest networks.
             6: Same as above with 5 guest networks.
             7: Same as above with 6 guest networks.
         8: Same as above with 7 guest networks.

         Bit 16: -- Admin Has control over Primary Wireless Network       :  65536
         Bit 17: -- Admin Has control over Guest Network 1 (interface 33) : 131072
         Bit 18: -- Admin Has control over Guest Network 2 (interface 34) : 262144
         Bit 19: -- Admin Has control over Guest Network 3 (interface 35) : 524288
         Bit 20: -- Admin Has control over Guest Network 4 (interface 36) :1048576
         Bit 21: -- Admin Has control over Guest Network 5 (interface 37) :2097152
         Bit 22: -- Admin Has control over Guest Network 6 (interface 38) :4194304
         Bit 23: -- Admin Has control over Guest Network 7 (interface 39) :8388608

         This object value is stored in non-vol and set to 1
         after factory reset."

    ::= { saRgDot11ExtMgmtEntry 17 }

saRgDot11ExtActualChannel OBJECT-TYPE
    SYNTAX      INTEGER
    MAX-ACCESS  read-only
    STATUS      current
    DESCRIPTION
        "Reports the current channel number that wireless is on.
         The value of 0 means wireless is disabled."
    ::= { saRgDot11ExtMgmtEntry 18 }

saRgDot11ExtOnOffPushButtonTime OBJECT-TYPE
    SYNTAX      INTEGER (0..11)
    UNITS       "seconds"
    MAX-ACCESS  read-write
    STATUS      current
    DESCRIPTION
        "Specifies how long to press WPS button to enable or disable
         the WiFi interface (primary SSID). When set to 11, the feature
         is disabled.
         Note that if the device has multiple radios but a single WPS HW button,
         only the first instance (saRgDot11ExtOnOffPushButtonTime.32) should be used.
         Stored in non-vol, 5, 10 after factory reset."
    ::= { saRgDot11ExtMgmtEntry 19 }

saRgDot11ExtWmm OBJECT-TYPE
    SYNTAX  INTEGER {
        disable(0),
        enable(1)
        }
    MAX-ACCESS  read-write
    STATUS      current
    DESCRIPTION
        "Mib to Enable/Disable Wifi-Multi Media (WMM) QOS fetures.
        This parameter is stored in non-vol and set to
        enable(1) after a factory reset."
    DEFVAL { 1 }
    ::= { saRgDot11ExtMgmtEntry 20 }

 saRgDot11ExtWmmNoAck OBJECT-TYPE
    SYNTAX  INTEGER {
        disable(0),
        enable(1)
        }
    MAX-ACCESS  read-write
    STATUS      current
    DESCRIPTION
        "Mib to control whether Wifi packets require acknowledgement.
        disable(0) Use acknowledgemnet for Wifi packets.
        enable(1)  Sets No acknowledgement which allows for higher throughput and lower latency when some
                   packetloss is acceptable (ex. VoIP).
        Note: If WMM is disabled then this setting has no effect, and you can Not disable Acks from being
        returned from the stations.
        This parameter is stored in non-vol and set to disable(0) after a factory reset."
    DEFVAL { 0 }
    ::= { saRgDot11ExtMgmtEntry 21 }

 saRgDot11ExtMulticastRate OBJECT-TYPE
    SYNTAX      INTEGER {
                                disable(0),
                mbits1(1),
                mbits2(2),
                mbits5-5(5),
                mbits6(6),
                mbits9(9),
                mbits11(11),
                mbits12(12),
                mbits18(18),
                mbits24(24),
                mbits36(36),
                mbits48(48),
                mbits54(54)
        }
    UNITS       "Mbps"
    MAX-ACCESS  read-write
    STATUS      current
    DESCRIPTION
        "Forces the dot11 multicast Phy transmission rate.
         Note that the 802.11b rates, including mbits1(1), mbits2(2),
         mbits5-5(5), and mbits11(11), are not available in 5GHz.
         This object is stored in non-vol and defaults to disable(0) after factory reset."
    DEFVAL { 0 }
    ::= { saRgDot11ExtMgmtEntry 22 }

saRgDot11ExtWirelessButtonOperation OBJECT-TYPE
    SYNTAX  INTEGER {
        disable(0),
        enable(1)
    }
    MAX-ACCESS    read-write
    STATUS        current
    DESCRIPTION
        "To enable or disable the button press of wireless ON/OFF button.
         This feature will work only on products that have the wireless ON/OFF button.
         This MIB will control if the Wireless ON/OFF button can be pressed or not.
         If it's enabled then button press would take effect otherwise there will not be any effect on button press.
         Note that if the device has multiple radios but a single Wireless ON/OFF button,
         only the first instance (saRgDot11ExtWirelessButtonOperation.32) should be used.
         By default value will be set to enable(1)."
    DEFVAL { 1 }
    ::= { saRgDot11ExtMgmtEntry 23 }


---------------------------------------
-- Dot11nExt - Radio Settings Table
---  Table to support Multiple 802.11n Radios
---  Note: Indexes may be set to support specific hardware interfaces.
---  Index 32 MUST match saRgDot11n.
---------------------------------------

saRgDot11nExt OBJECT IDENTIFIER ::= { saRgDot11 7 }

saRgDot11nExtTable  OBJECT-TYPE
    SYNTAX      SEQUENCE OF SaRgDot11nExtEntry
    MAX-ACCESS  not-accessible
    STATUS      current
    DESCRIPTION
        "Multiple 802.11n Radio Configuration Table
                 Index 32 should be set for Radio 0 -- 2.4 GHz if populated.
                 Index 112 should be set for Radio 1"
    ::= { saRgDot11nExt 1 }

saRgDot11nExtEntry OBJECT-TYPE
    SYNTAX      SaRgDot11nExtEntry
    MAX-ACCESS  not-accessible
    STATUS      current
    DESCRIPTION
        "A row in the table which represents parameters for an 802.11n Radio."
    INDEX   { ifIndex }
    ::= { saRgDot11nExtTable 1 }

SaRgDot11nExtEntry ::=
    SEQUENCE {
                saRgdot11nExtMode               INTEGER,
                saRgdot11nExtPhyRate            INTEGER,
                saRgdot11nExtBand               INTEGER,
                saRgdot11nExtBandWidth          INTEGER,
                saRgdot11nExtSideBand           INTEGER,
                saRgdot11nExtObssCoex           INTEGER,
                saRgdot11nExtMulticastRate      INTEGER
        }

saRgdot11nExtMode OBJECT-TYPE
    SYNTAX INTEGER {
        auto(1),
        off(2),
        n-only(3),
        b-mode(16),
        g-mode(32),
        bg-mode(48),
        a-mode(64),
        n-only(128),
        gn-mode(160),
        bgn-mode(176),
        an-mode(192),
        ac-only(256),
        nac-only(384),
        anac-mode(448)
        }
    MAX-ACCESS  read-write
    STATUS      current
    DESCRIPTION
        "Determines which 802.11 mode the radio will run in.
         This object must be set by either the legacy or bitmask method.

         In legacy method,
         auto(1)  : supports all the 802.11 modes available in the radio.
         off(2)   : supports the legacy mode only (11b/g in 2.4GHz and 11a in 5GHz).
         n-only(3): accepts 11n-capable clients only but supports all the modes available in the radio.

         In bitmask method,
         b-mode(16)    : supports 11b mode in 2.4GHz.
         g-mode(32)    : supports 11g mode in 2.4GHz.
         bg-mode(48)   : supports 11b/g mode in 2.4GHz (16+32).
         a-mode(64)    : supports 11a mode in 5GHz.
         n-only(128)   : accepts 11n-capable clients only but supports both legacy and 11n modes in 2.4GHz or 5GHz.
         gn-mode(160)  : supports 11g/n mode in 2.4GHz (32+128).
         bgn-mode(176) : supports all 11b/g/n modes in 2.4GHz (16+32+128).
         an-mode(192)  : supports 11a/n modes in 5GHz (64+128).
         ac-only(256)  : accepts 11ac-capable clients only but supports 11a/n/ac modes in 5GHz.
         nac-only(384) : accepts 11n-capable clients only but supports 11a/n/ac modes in 5GHz (128+256).
         anac-mode(448): supports all 11a/n/ac modes in 5GHz (64+128+256).

         Note: Some options may not be available depending on the radio model.
         Note: The change of this object value will also affect other MIB selections, including saRgdot11nExtBandWidth.
         This object is stored in non-vol and defaults to auto(1) after factory reset."
     ::= { saRgDot11nExtEntry 1 }

saRgdot11nExtPhyRate OBJECT-TYPE
    SYNTAX INTEGER {
        auto(0),
        legacy(1),
        mbits6-5or13-5(2),
        mbits13or27(3),
        mbits19-5or40-5(4),
        mbits26or54(5),
        mbits39or81(6),
        mbits52or108(7),
        mbits58-5or121-5(8),
        mbits65or135(9),
        reserved1(10),
        reserved2(11),
        reserved3(12),
        reserved4(13),
        mbits78or162(14),
        mbits104or216(15),
        mbits117or243(16),
        mbits130or270(17)
        }
    MAX-ACCESS  read-write
    STATUS      current
    DESCRIPTION
        "Forces the N Phy transmission rate for the AP to a particular speed.  Each pair of rates
         corresponds to a 20 MHz or 40 MHz channel configuration.
         This object is stored in non-vol and defaults to auto(0) after factory reset.

         This MIB is being degraded, since it is better for higher band width devices to run in 'auto' mode"
    DEFVAL { auto }
    ::= { saRgDot11nExtEntry 2 }


saRgdot11nExtBand OBJECT-TYPE
    SYNTAX INTEGER {
        band-2-4G(1),
        band-5G(2)
        }
    MAX-ACCESS  read-write
    STATUS      current
    DESCRIPTION
        "Determines which Band that we will be operating in. Either the 2.4G or the 5G Hz.
         Note: This is for N cards only.
         This object is stored in non-vol and defaults to band-2-4G(1) after factory reset."
    ::= { saRgDot11nExtEntry 3 }

saRgdot11nExtBandWidth OBJECT-TYPE
    SYNTAX INTEGER {
        width-20MHz(1),
        width-40MHz(2),
        width-80MHz(3)
        }
    MAX-ACCESS  read-write
    STATUS      current
    DESCRIPTION
        "Determines which Band Width that we will be operating in. Either the 20MHz or the 40MHz.
         Note: This is for N cards only, and this also affect other MIB selections such as saRgdot11nSideBand.
         The 80 MHz channel width is only applicable for 802.11ac capable cards. If a user sets this to 80 MHz, SNMPset would fail for non-802.11ac cards
         This object is stored in non-vol and defaults to ? after factory reset."
    ::= { saRgDot11nExtEntry 4 }

saRgdot11nExtSideBand OBJECT-TYPE
    SYNTAX INTEGER {
        upper(1),
        lower(2)
        }
    MAX-ACCESS  read-write
    STATUS      current
    DESCRIPTION
        "Determines which side Band the channel will operate in.
         Note: This is for N cards only, this mib is dependent of what saRgdot11nBandWidth is selected and only
         applies when 40MHz is selected.
         This object is stored in non-vol and defaults to lower(2) after factory reset."
    ::= { saRgDot11nExtEntry 5 }

saRgdot11nExtObssCoex OBJECT-TYPE
        SYNTAX INTEGER {
                disable(0),
                enable(1)
                }
        MAX-ACCESS read-write
        STATUS     current
        DESCRIPTION
                "Allows MSO to control OBSS (Overlapping BSS) Coexistance parameter for 802.11n 40MHz channel width.
                 By default it is enabled and is stored in non-vol
                 Factory reset would clear it and would be enable(1) after factory reset.
                 When disabled, the 802.11n Wifi would stay in 40 MHz channel-width inspite of interference from other
                 wifi channels. While enabled, 802.11n would coexist with 802.11g channels using 20 MHz default channel-width
                 "
        ::= { saRgDot11nExtEntry 6 }

saRgdot11nExtMulticastRate OBJECT-TYPE
    SYNTAX INTEGER {
        disable(0),
        legacy(1),
        mbits6-5or13-5(2),
        mbits13or27(3),
        mbits19-5or40-5(4),
        mbits26or54(5),
        mbits39or81(6),
        mbits52or108(7),
        mbits58-5or121-5(8),
        mbits65or135(9),
        reserved1(10),
        reserved2(11),
        reserved3(12),
        reserved4(13),
        mbits78or162(14),
        mbits104or216(15),
        mbits117or243(16),
        mbits130or270(17)
        }
    MAX-ACCESS  read-write
    STATUS      current
    DESCRIPTION
        "Forces the dot11n Multicast Phy transmission rate.  Legacy mode forces the rate to be set
                 by dot11MulticastRate.
         This object is stored in non-vol and defaults to disable(0) after factory reset."
    DEFVAL { 0 }
    ::= { saRgDot11nExtEntry 7 }


-- saRgDot11ApplySettings: do 'on the fly' config with settings from above.
-- This scalar object was placed by itself at ieee802saRgDot11Mgmt 100 because
-- it applies all settings from all current and possibly future 802.11
-- groups.  Wanted to leave plenty of room to add new groups in the future.

saRgDot11ApplySettings OBJECT-TYPE
    SYNTAX      TruthValue
    MAX-ACCESS  read-write
    STATUS      current
    DESCRIPTION
        "If set to true(1), then all the settings (MIB values)
         from this MIB tree will be applied to run time configuration,
         modifying previous RG operation with the new settings.
         Before setting the value to true, MIBs modified in the MIB
         tree are stored in non-vol and will not modify RG operation
         until saRgDot11ApplySettings is set to true or CM resets.
         Note: this applies only to the MIB objects that are stored
         in non-vol.
         Always returns false(2) when read."
    ::= { saRgDot11 1001 }


-- =============
-- IP management
-- =============

saRgIpMgmt OBJECT IDENTIFIER ::=  { saRg 3 }


-- { saRgIpMgmt 1 } reserved for WAN IP definition (currently only DHCP)


-- LAN NETWORK DEFINITIONS

saRgIpMgmtLanTable OBJECT-TYPE
    SYNTAX SEQUENCE OF SaRgIpMgmtLanEntry
    MAX-ACCESS not-accessible
    STATUS current
    DESCRIPTION
            "Networks on the LAN side.
             Primary BSS stored in non-vol."
    ::= { saRgIpMgmt 2 }

saRgIpMgmtLanEntry OBJECT-TYPE
    SYNTAX      SaRgIpMgmtLanEntry
    MAX-ACCESS  not-accessible
    STATUS     current
    DESCRIPTION
            "List of networks on the LAN side."
    INDEX { ifIndex }
    ::= { saRgIpMgmtLanTable 1 }

SaRgIpMgmtLanEntry ::= SEQUENCE {
    saRgIpMgmtLanMode              INTEGER,
    saRgIpMgmtLanNetwork           IpAddress,
    saRgIpMgmtLanNetworksAllow     INTEGER,
    saRgIpMgmtLanSubnetMask        IpAddress,
    saRgIpMgmtLanGateway           IpAddress,
    saRgIpMgmtLanDhcpServer        INTEGER,
    saRgIpMgmtLanNapt              INTEGER,
    saRgIpMgmtLanTypeOfService     INTEGER,
    saRgIpMgmtLanDhcp125Option     INTEGER,
    saRgIpMgmtLanHnap                  INTEGER,
        saRgIpMgmtLanUpnp                          INTEGER,
        saRgIpMgmtLanDhcpOption43      SnmpAdminString,
    }

saRgIpMgmtLanMode OBJECT-TYPE
    SYNTAX INTEGER {
        bridge(1),
        router(2),
        l2tpv2-client(3),
        mixed(4),
        vlan(5)
        }
    MAX-ACCESS    read-write
    STATUS        current
    DESCRIPTION
        "Defines the mode of operation for the device.
        Setting this object via SNMP for the primary BSS will cause
        the unit to reboot.
        Setting this object via SNMP for the secondary BSSs will not
        cause the unit to reboot.
        The value for primary BSS is stored in non-vol and is router
        after factory reset.
        The default value for other BSSs is router.
                This MIB supersedes saRgDeviceMode for the .32 interface.
        l2tpv2-client(3)is obsoleted and NOT supported.

                bridge(1):      Sets individual interface to bridging mode
                                        (for IPv6 interfaces DHCPv6 is external)
                router(2):      Sets individual interface to routing mode
                                        (for IPv6 interfaces DHCPv6 is internal)
                l2tpv2-client(3): <obsolete>
                mixed(4):       For mixed mode. This setting is applicable only to
                                        .32 interface. This value is used on conjunction with
                                        saRgIpMgmtLanPortControlTable
                                        *Note: mixed(4) mode NOT Supported by DOCSIS 2.0 products.
                vlan (5):       Enables the vlan control feature.
                                        See saRgVlanTable MIBs for VLAN configuration information."
    DEFVAL { 2 }
    ::= { saRgIpMgmtLanEntry 1 }

saRgIpMgmtLanNetwork OBJECT-TYPE
    SYNTAX      IpAddress
    MAX-ACCESS  read-write
    STATUS      current
    DESCRIPTION
            "The LAN-Trans network number.
            Default for primary BSS is 192.168.0.0
            Default for other BSSs is 192.168.ifIndex.0"
    ::= { saRgIpMgmtLanEntry 3 }


saRgIpMgmtLanNetworksAllow OBJECT-TYPE
                SYNTAX  INTEGER {
                default(0),
                anyPrivateClass(1),
                anyClass(2)
        }
    MAX-ACCESS  read-write
    STATUS      current
    DESCRIPTION
                "Allows the user via the internal Web GUI (Lan Setup page
                to input an IPv4 public or private Local IP address other than a
                class C Private address (the default Network for the Primary BSS = 192.168.0.0/24, with
                the default Local Ip address = 192.168.0.1.)
                In all cases the mask must be 255.255.255.x since the RG is limited to supporting
                a maximum of 253 IP addresses.
                (See RFC1918 for a description of private IP addresses and specified ranges.)
                Available Mib settings:
                default(0):                     Only the third and fourth octets are editable in
                                                        the Web GUI for the Local IP address (Ex. 192.168.x.x/24).
                anyPrivateClass(1):     All 4 octets are editable in the Web GUI for Local IP address, but
                                                        the network specified must be a Private class A, B or C network address.
                                                        (Ex. A=10.x.x.x, B=172.16.x.x, C=192.168.x.x).
                anyClass(2):            All 4 octets are editable in the Web GUI for Local IP address, and
                                                        the network specified could be any public or private class A, B, or C address.

                If the MSO specifically sets a Local IP address in saRgIpMgmtLanNetwork to a value other than
                the default value (for example: 192.168.0.1) then these fields will be uneditable by the user (grayed out)."
        DEFVAL { 0 }
        ::= { saRgIpMgmtLanEntry 4 }

saRgIpMgmtLanSubnetMask OBJECT-TYPE
    SYNTAX      IpAddress
    MAX-ACCESS  read-write
    STATUS      current
    DESCRIPTION
            "The device MUST provide the value of this MIB
            object in the Option 1 (Subnet Mask) of
            DHCP OFFER and ACK messages sent to a LAN IP Device."
    DEFVAL { 'ffffff00'h }    -- 255.255.255.0
    ::= { saRgIpMgmtLanEntry 5 }

saRgIpMgmtLanGateway OBJECT-TYPE
    SYNTAX      IpAddress
    MAX-ACCESS  read-write
    STATUS      current
    DESCRIPTION
                "The type of this address is specified by
            saRgIpMgmtLanNetwokRouterType. The PS MUST
            provide the value of this MIB object in the
            Option 3 (Router IP address) of the DHCP
            OFFER and ACK messages sent to the LAN IP Device.
            Default for primary BSS is 192.168.0.1
            Default for other BSSs is 192.168.ifIndex.1"
    ::= { saRgIpMgmtLanEntry 7 }

saRgIpMgmtLanDhcpServer OBJECT-TYPE
    SYNTAX INTEGER {
        disable(0),
        enable(1)
        }
    MAX-ACCESS    read-write
    STATUS        current
    DESCRIPTION
        "The value for primary BSS is stored in non-vol.
         The default value for other BSSs is:
         Enabled by default if interface is in router mode.
         Always disabled if interface is in bridge mode."
    ::= { saRgIpMgmtLanEntry 8 }

saRgIpMgmtLanNapt OBJECT-TYPE
    SYNTAX INTEGER {
        disable(0),
        enable(1)
        }
    MAX-ACCESS    read-write
    STATUS        current
    DESCRIPTION
        "The value for primary BSS is stored in non-vol.
         The default value for other BSSs is:
         Enabled by default if interface is in router mode.
         Always disabled if interface is in bridge mode."
    ::= { saRgIpMgmtLanEntry 9 }

saRgIpMgmtLanTypeOfService OBJECT-TYPE
      SYNTAX      INTEGER
      MAX-ACCESS  read-write
      STATUS      current
      DESCRIPTION
          "Definition of the TOS bits for the Network.
           This object does not apply to primary BSS."
      DEFVAL { 0 }
      ::= { saRgIpMgmtLanEntry 10 }

saRgIpMgmtLanDhcp125Option OBJECT-TYPE
      SYNTAX      INTEGER {
        disable(0),
        addSsidName(1)
        }
      MAX-ACCESS  read-write
      STATUS      current
      DESCRIPTION
          "This option controls if the RG adds a Cisco specific
           suboption (number 17) to DHCP DISCOVER and REQUEST
           from the clients that are bridged on the BSS:
         0: do not add the option
         1: add suboption 17 to Cisco specific enterprise-id
            (9) within DHCP option 125. The content is the SSID name."
      DEFVAL { 0 }
      ::= { saRgIpMgmtLanEntry 11 }

saRgIpMgmtLanHnap OBJECT-TYPE
    SYNTAX INTEGER {
        disable(0),
        enable(1)
        }
    MAX-ACCESS    read-write
    STATUS        current
    DESCRIPTION
        "The value for primary BSS is stored in non-vol and
         is enable after factory default.
         The default value for other BSSs is disable."
    ::= { saRgIpMgmtLanEntry 12 }

saRgIpMgmtLanUpnp OBJECT-TYPE
    SYNTAX INTEGER {
        disable(0),
        enable(1)
        }
    MAX-ACCESS    read-write
    STATUS        current
    DESCRIPTION
        "Enable/Disable the UPnP agent.
             The value is stored in non-vol and is disabled after factory default for the primary SSID.
                     The UPnP agents for additional networks are enabled by default.
         "
    DEFVAL { 0 }
    ::= { saRgIpMgmtLanEntry 13 }

saRgIpMgmtLanDhcpOption43 OBJECT-TYPE
    SYNTAX      SnmpAdminString
    MAX-ACCESS  read-write
    STATUS      current
    DESCRIPTION
         "If option 60 is set from the CPE then return this value in option 43 of the DHCP Reply.
         If this value is null then do not reply with option 43 (default is null)
         This MIB will apply to the Primary SSID (intface .32) only"
    ::= { saRgIpMgmtLanEntry 14 }

-- LAN DHCP SERVERS DEFINITIONS

saRgIpMgmtLanDhcpServerTable OBJECT-TYPE
    SYNTAX SEQUENCE OF SaRgIpMgmtLanDhcpServerEntry
    MAX-ACCESS not-accessible
    STATUS current
    DESCRIPTION
            "Networks on the LAN side.
             Stored in non-vol. .10-.128 for primary BSS
             after factory reset."
    ::= { saRgIpMgmt 3 }

saRgIpMgmtLanDhcpServerEntry OBJECT-TYPE
    SYNTAX      SaRgIpMgmtLanDhcpServerEntry
    MAX-ACCESS  not-accessible
    STATUS     current
    DESCRIPTION
            "List of networks on the LAN side."
    INDEX { ifIndex }
    ::= { saRgIpMgmtLanDhcpServerTable 1 }

SaRgIpMgmtLanDhcpServerEntry ::= SEQUENCE {
    saRgIpMgmtLanDhcpServerPoolStart         IpAddress,
    saRgIpMgmtLanDhcpServerPoolEnd           IpAddress,
    saRgIpMgmtLanDhcpServerLeaseTime         Unsigned32,
    saRgIpMgmtLanDhcpServerTimeOffset        Integer32,
        saRgIpMgmtLanDhcpServerDomainName        SnmpAdminString,
    }


saRgIpMgmtLanDhcpServerPoolStart OBJECT-TYPE
    SYNTAX      IpAddress
    MAX-ACCESS  read-write
    STATUS      current
    DESCRIPTION
            "The start of range LAN Trans IP Addresses. The type of
            this address is specified by saRgIpMgmtLanDhcpServerPoolStartType.
            Default value depends on IP network and subnet."
    ::= { saRgIpMgmtLanDhcpServerEntry 2 }

saRgIpMgmtLanDhcpServerPoolEnd OBJECT-TYPE
    SYNTAX      IpAddress
    MAX-ACCESS  read-write
    STATUS      current
    DESCRIPTION
            "The end of range for LAN-Trans IP Addresses. The type of
            this address is specified by saRgIpMgmtLanDhcpServerPoolEndType.
            Default value depends on IP network and subnet."
    ::= { saRgIpMgmtLanDhcpServerEntry 4 }

saRgIpMgmtLanDhcpServerLeaseTime OBJECT-TYPE
    SYNTAX      Unsigned32
    UNITS       "seconds"
    MAX-ACCESS  read-write
    STATUS      current
    DESCRIPTION
            "The PS MUST provide the value of this MIB object in the
            Option 51 (IP Address lease time) of the DHCP OFFER and
            ACK messages sent to the LAN IP Device."
    DEFVAL { 3600 }
    ::= { saRgIpMgmtLanDhcpServerEntry 5 }

saRgIpMgmtLanDhcpServerTimeOffset OBJECT-TYPE
    SYNTAX      Integer32 (-86400..86400) -- 0 to 24 hours (in seconds)
    UNITS       "seconds"
    MAX-ACCESS  read-write
    STATUS      current
    DESCRIPTION
            "The PS MUST provide the value of this MIB object in
            the Option 2 (Time Offset from Coordinated
            Universal Time-UTC) in the DHCP OFFER and ACK
            messages sent to the LAN IP Device."
    DEFVAL { 0 }    -- UTC
    ::= { saRgIpMgmtLanDhcpServerEntry 6 }

saRgIpMgmtLanDhcpServerDomainName OBJECT-TYPE
    SYNTAX      SnmpAdminString
    MAX-ACCESS  read-write
    STATUS      current
    DESCRIPTION
            "This is the domain name given to this DHCP server's clients."
    ::= { saRgIpMgmtLanDhcpServerEntry 7 }

--====================================================================
--
--    saRgIpMgmtLanAddrTable (CDP LAN Address Table)
--
--    The saRgIpMgmtLanAddrTable contains the DHCP parameters
--    for each IP address served to the LAN-Trans realm.
--
--=========================================================================

saRgIpMgmtLanAddrTable OBJECT-TYPE
       SYNTAX      SEQUENCE OF SaRgIpMgmtLanAddrEntry
       MAX-ACCESS  not-accessible
       STATUS      current
       DESCRIPTION
               "IP addresses of devices served by DHCP servers."
    ::= { saRgIpMgmt 4 }

saRgIpMgmtLanAddrEntry OBJECT-TYPE
    SYNTAX      SaRgIpMgmtLanAddrEntry
    MAX-ACCESS  not-accessible
    STATUS      current
    DESCRIPTION
            "List of general parameters pertaining to LAN-Trans IP
            address reservations and leases."
    INDEX { ifIndex, saRgIpMgmtLanAddrIndex }
    ::= { saRgIpMgmtLanAddrTable 1 }

SaRgIpMgmtLanAddrEntry ::= SEQUENCE {
    saRgIpMgmtLanAddrIndex              INTEGER,
    saRgIpMgmtLanAddrIp                 IpAddress,
    saRgIpMgmtLanAddrPhysAddr           PhysAddress,
    saRgIpMgmtLanAddrLeaseCreateTime    DateAndTime,
    saRgIpMgmtLanAddrLeaseExpireTime    DateAndTime,
    saRgIpMgmtLanAddrHostName           SnmpAdminString,
    saRgIpMgmtLanAddrClientId           SnmpAdminString,
    saRgIpMgmtLanAddrInterface          SnmpAdminString,
        saRgIpMgmtLanAddrClientNotes        SnmpAdminString,
        saRgIpMgmtLanAddrCpeStatus          INTEGER,
    }

saRgIpMgmtLanAddrIndex OBJECT-TYPE
    SYNTAX      INTEGER
    MAX-ACCESS  not-accessible
    STATUS      current
    DESCRIPTION
            "The index of the the LAN IP Device in the LAN-Trans Realm."
    ::= { saRgIpMgmtLanAddrEntry 1 }

saRgIpMgmtLanAddrIp OBJECT-TYPE
    SYNTAX      IpAddress
    MAX-ACCESS  read-only
    STATUS      current
    DESCRIPTION
            ""
    ::= { saRgIpMgmtLanAddrEntry 3 }

saRgIpMgmtLanAddrPhysAddr OBJECT-TYPE
    SYNTAX      PhysAddress
    MAX-ACCESS  read-only
    STATUS      current
    DESCRIPTION
            "The client's (i.e., LAN IP Device's) hardware address as
            indicated in the chaddr field of its DHCP REQUEST message."
    ::= { saRgIpMgmtLanAddrEntry 4 }

saRgIpMgmtLanAddrLeaseCreateTime OBJECT-TYPE
    SYNTAX      DateAndTime
    MAX-ACCESS  read-only
    STATUS      current
    DESCRIPTION
            "This is the date and time when the LAN IP lease was
            created (if it has not yet been renewed) or last renewed."
    ::= { saRgIpMgmtLanAddrEntry 5 }

saRgIpMgmtLanAddrLeaseExpireTime OBJECT-TYPE
    SYNTAX      DateAndTime
    MAX-ACCESS  read-only
    STATUS      current
    DESCRIPTION
            "This is the date and time when the LAN IP address lease
            expired or will expire."
    ::= { saRgIpMgmtLanAddrEntry 6 }


saRgIpMgmtLanAddrHostName OBJECT-TYPE
    SYNTAX      SnmpAdminString
    MAX-ACCESS  read-only
    STATUS      current
    DESCRIPTION
            "This is the Host Name of the LAN IP address, based on DCHP
            option 12."
    ::= { saRgIpMgmtLanAddrEntry 7 }

saRgIpMgmtLanAddrClientId OBJECT-TYPE
    SYNTAX      SnmpAdminString
    MAX-ACCESS  read-only
    STATUS      current
    DESCRIPTION
            "This is the Client Class Identifier, based on DHCP option 60."
    ::= { saRgIpMgmtLanAddrEntry 8 }

saRgIpMgmtLanAddrInterface OBJECT-TYPE
    SYNTAX      SnmpAdminString
    MAX-ACCESS  read-only
    STATUS      current
    DESCRIPTION
            "This will show the associated interface (LAN, WiFi or MoCA) of the connected CPE."
    ::= { saRgIpMgmtLanAddrEntry 9 }

saRgIpMgmtLanAddrClientNotes OBJECT-TYPE
    SYNTAX      SnmpAdminString
    MAX-ACCESS  read-only
    STATUS      current
    DESCRIPTION
            "This will show the associated client notes for the connected CPE."
    ::= { saRgIpMgmtLanAddrEntry 10 }

saRgIpMgmtLanAddrCpeStatus OBJECT-TYPE
    SYNTAX INTEGER {
        offline(0),
        online(1)
        }
    MAX-ACCESS    read-only
    STATUS        current
    DESCRIPTION
        "This MIB shows the client's current online status.
                - 0 - The client currently has no connectivity.
                - 1 - The client currently has connectivity and is online.
                "
    DEFVAL { 0 }
    ::= { saRgIpMgmtLanAddrEntry 11 }

--===================================================================
--
-- saRgIpMgmtDnsServerTable (CDP WAN DNS Server Table)
--
-- The saRgIpMgmtDnsServerTable is a table of 3 cable network
-- and Internet DNS Servers.
--
--===================================================================

saRgIpMgmtDnsServerTable OBJECT-TYPE
    SYNTAX SEQUENCE OF SaRgIpMgmtDnsServerEntry
    MAX-ACCESS not-accessible
    STATUS current
    DESCRIPTION
            "This table contains the IP addresses of cable network and
            Internet DNS servers, in the order of preference in which
            the PS's CNP will query them, when it cannot resolve a DNS
            query using local information. Entries in this table are
            updated with the information contained in DHCP Option 6,
            received during both the WAN-Man and WAN-Data IP
            acquisition processes.
            Stored in non-vol and 0.0.0.0 for all servers after
            factory reset."
    ::= { saRgIpMgmt 5 }

saRgIpMgmtDnsServerEntry OBJECT-TYPE
    SYNTAX      SaRgIpMgmtDnsServerEntry
    MAX-ACCESS  not-accessible
    STATUS     current
    DESCRIPTION
            "List of cable network and Internet DNS servers."
    INDEX { saRgIpMgmtDnsServerOrder }
    ::= { saRgIpMgmtDnsServerTable 1 }

SaRgIpMgmtDnsServerEntry ::= SEQUENCE {
    saRgIpMgmtDnsServerOrder  INTEGER,
    saRgIpMgmtDnsServerIp     IpAddress,
	saRgIpMgmtDnsServerIpv6   InetAddress
    }

saRgIpMgmtDnsServerOrder OBJECT-TYPE
    SYNTAX      INTEGER {
                    primary(1),
                    secondary(2),
                    tertiary(3)
                }
    MAX-ACCESS  not-accessible
    STATUS      current
    DESCRIPTION
            "The order of preference for cable network and Internet DNS
            servers, as listed in DHCP option 6 (Domain Server)."
    ::= { saRgIpMgmtDnsServerEntry 1 }

saRgIpMgmtDnsServerIp OBJECT-TYPE
    SYNTAX      IpAddress
    MAX-ACCESS  read-write
    STATUS      current
    DESCRIPTION
            "This parameter indicates the IP address of a WAN DNS
            server."
    ::= { saRgIpMgmtDnsServerEntry 3 }

saRgIpMgmtDnsServerIpv6 OBJECT-TYPE
    SYNTAX      InetAddress
    MAX-ACCESS  read-write
    STATUS      current
    DESCRIPTION
            "This parameter indicates the IPv6 address of a WAN DNS
            server."
    ::= { saRgIpMgmtDnsServerEntry 4 }


--==============================
-- LAN DHCP fixed IP assignments
--==============================

saRgIpMgmtDhcpFixedIpTable OBJECT-TYPE
    SYNTAX      SEQUENCE OF SaRgIpMgmtDhcpFixedIpEntry
    MAX-ACCESS  not-accessible
    STATUS      current
    DESCRIPTION
        "Fixed IP address assignments for DHCP server.
         Table does not return any row if DHCP disabled.
         The value for primary BSS is stored in non-vol."
    ::= { saRgIpMgmt 6 }

saRgIpMgmtDhcpFixedIpEntry OBJECT-TYPE
    SYNTAX      SaRgIpMgmtDhcpFixedIpEntry
    MAX-ACCESS  not-accessible
    STATUS      current
    DESCRIPTION
            "List of general parameters pertaining to LAN-Trans IP
            address reservations and leases."
    INDEX { ifIndex, saRgIpMgmtDhcpFixedIpIndex }
    ::= { saRgIpMgmtDhcpFixedIpTable 1 }

SaRgIpMgmtDhcpFixedIpEntry ::= SEQUENCE {
    saRgIpMgmtDhcpFixedIpIndex              INTEGER,
    saRgIpMgmtDhcpFixedIpRowStatus          RowStatus,
    saRgIpMgmtDhcpFixedIpAddress            IpAddress,
    saRgIpMgmtDhcpFixedIpPhysAddr           PhysAddress,
    saRgIpMgmtDhcpFixedIpHostName           SnmpAdminString
    }

saRgIpMgmtDhcpFixedIpIndex OBJECT-TYPE
    SYNTAX      INTEGER (1..16)
    MAX-ACCESS  not-accessible
    STATUS      current
    DESCRIPTION
            "The index of the the LAN IP Device in the LAN-Trans Realm."
    ::= { saRgIpMgmtDhcpFixedIpEntry 1 }

saRgIpMgmtDhcpFixedIpRowStatus OBJECT-TYPE
    SYNTAX      RowStatus
    MAX-ACCESS  read-write
    STATUS      current
    DESCRIPTION
            "The row status. A row can be destroyed."
    ::= { saRgIpMgmtDhcpFixedIpEntry 2 }

saRgIpMgmtDhcpFixedIpAddress OBJECT-TYPE
    SYNTAX      IpAddress
    MAX-ACCESS  read-write
    STATUS      current
    DESCRIPTION
            ""
    ::= { saRgIpMgmtDhcpFixedIpEntry 4 }

saRgIpMgmtDhcpFixedIpPhysAddr OBJECT-TYPE
    SYNTAX      PhysAddress
    MAX-ACCESS  read-create
    STATUS      current
    DESCRIPTION
            "The client's (i.e., LAN IP Device's) hardware address as
            indicated in the chaddr field of its DHCP REQUEST message."
    ::= { saRgIpMgmtDhcpFixedIpEntry 5 }

saRgIpMgmtDhcpFixedIpHostName OBJECT-TYPE
    SYNTAX      SnmpAdminString(SIZE(0..80))
    MAX-ACCESS  read-write
    STATUS      current
    DESCRIPTION
            "This is the Host Name of the LAN IP address, based on DCHP
            option 12."
    ::= { saRgIpMgmtDhcpFixedIpEntry 6 }

-- ==============
-- NAT parameters

saRgIpMgmtNat OBJECT IDENTIFIER ::=  { saRgIpMgmt 7 }

saRgIpMgmtNatTcpWait OBJECT-TYPE
    SYNTAX      Unsigned32 (1..65535)
    UNITS       "seconds"
    MAX-ACCESS  read-write
    STATUS      current
    DESCRIPTION
        "Configures the NAT session time for TCP in seconds.
         Stored in non-vol, set to 300 after factory reset."
    ::= { saRgIpMgmtNat 1 }

saRgIpMgmtNatUdpWait OBJECT-TYPE
    SYNTAX      Unsigned32 (1..65535)
    UNITS       "seconds"
    MAX-ACCESS  read-write
    STATUS      current
    DESCRIPTION
        "Configures the NAT session time for UDP in seconds.
         Stored in non-vol, set to 300 after factory reset."
    ::= { saRgIpMgmtNat 2 }

saRgIpMgmtNatIcmpWait OBJECT-TYPE
    SYNTAX      Unsigned32 (1..65535)
    UNITS       "seconds"
    MAX-ACCESS  read-write
    STATUS      current
    DESCRIPTION
        "Configures the NAT session time for ICMP in seconds.
         Stored in non-vol, set to 2 after factory reset."
    ::= { saRgIpMgmtNat 3 }

-- ==============
-- Static routing

saRgIpMgmtStaticRouteTable OBJECT-TYPE
    SYNTAX SEQUENCE OF SaRgIpMgmtStaticRouteEntry
    MAX-ACCESS not-accessible
    STATUS current
    DESCRIPTION
        "Static route entries in the routing table.
         This table is saved in non-vol and is empty
         after factory reset."
    ::= { saRgIpMgmt 8 }

saRgIpMgmtStaticRouteEntry OBJECT-TYPE
    SYNTAX      SaRgIpMgmtStaticRouteEntry
    MAX-ACCESS  not-accessible
    STATUS     current
    DESCRIPTION
        "List of static route entries in the routing table."
    INDEX { saRgIpMgmtStaticRouteIndex }
    ::= { saRgIpMgmtStaticRouteTable 1 }

SaRgIpMgmtStaticRouteEntry ::= SEQUENCE {
    saRgIpMgmtStaticRouteIndex         INTEGER,
    saRgIpMgmtStaticRouteRowStatus     RowStatus,
    saRgIpMgmtStaticRouteNetwork       IpAddress,
    saRgIpMgmtStaticRouteSubnetMask    IpAddress,
    saRgIpMgmtStaticRouteGateway       IpAddress,
    saRgIpMgmtStaticRouteRipAdvertise  TruthValue
    }

saRgIpMgmtStaticRouteIndex OBJECT-TYPE
    SYNTAX      INTEGER (1..16)
    MAX-ACCESS  not-accessible
    STATUS      current
    DESCRIPTION
        "The index of the the table."
    ::= { saRgIpMgmtStaticRouteEntry 1 }

saRgIpMgmtStaticRouteRowStatus OBJECT-TYPE
    SYNTAX      RowStatus
    MAX-ACCESS  read-write
    STATUS      current
    DESCRIPTION
        "The row status."
    ::= { saRgIpMgmtStaticRouteEntry 2 }

saRgIpMgmtStaticRouteNetwork OBJECT-TYPE
    SYNTAX      IpAddress
    MAX-ACCESS  read-write
    STATUS      current
    DESCRIPTION
        "Static route IP network definition"
    ::= { saRgIpMgmtStaticRouteEntry 3 }

saRgIpMgmtStaticRouteSubnetMask OBJECT-TYPE
    SYNTAX      IpAddress
    MAX-ACCESS  read-write
    STATUS      current
    DESCRIPTION
        "Static route network mask definition"
    ::= { saRgIpMgmtStaticRouteEntry 4 }

saRgIpMgmtStaticRouteGateway OBJECT-TYPE
    SYNTAX      IpAddress
    MAX-ACCESS  read-write
    STATUS      current
    DESCRIPTION
        "Gateway to the network defined in
         saRgIpMgmtStaticRouteNetwork and
         saRgIpMgmtStaticRouteSubnetMask."
    ::= { saRgIpMgmtStaticRouteEntry 5 }

saRgIpMgmtStaticRouteRipAdvertise OBJECT-TYPE
    SYNTAX      TruthValue
    MAX-ACCESS  read-write
    STATUS      current
    DESCRIPTION
        "If set to true(1), then static route entry
         will be advertised in RIP."
    DEFVAL { false }
    ::= { saRgIpMgmtStaticRouteEntry 6 }

-- WAN interface

saRgIpMgmtWanAddr OBJECT IDENTIFIER ::= { saRgIpMgmt 9 }

saRgIpMgmtWanAddrBase OBJECT IDENTIFIER ::= { saRgIpMgmtWanAddr 1 }

saRgIpMgmtWanMode OBJECT-TYPE
    SYNTAX INTEGER {
        dhcp(1),
        static(2),
        dualIp(3)
        }
    MAX-ACCESS    read-write
    STATUS        current
    DESCRIPTION
        "When dualIp(3) is selected, the second IP stack is used for
         user operations.
         Stored in non-vol, dhcp(1) after factory reset."
    ::= { saRgIpMgmtWanAddrBase 1 }

saRgIpMgmtWanMtu OBJECT-TYPE
    SYNTAX INTEGER (0..1500)
    UNITS       "bytes"
    MAX-ACCESS     read-write
    STATUS         current
    DESCRIPTION
        "MTU size for the IP layer. Valid range is 256 to 1500.
         0 is the default which is 1500.
         Stored in non-vol, 0 after factory reset."
    ::= { saRgIpMgmtWanAddrBase 2 }

saRgIpMgmtWanTtl OBJECT-TYPE
    SYNTAX INTEGER (0..255)
    UNITS       "hops"
    MAX-ACCESS     read-write
    STATUS         current
    DESCRIPTION
        "TTL for the IP packets forwarded to WAN.
         0 means no change to the original TTL (after
         being decreased by 1).
         Stored in non-vol, 0 after factory reset."
    ::= { saRgIpMgmtWanAddrBase 3 }


saRgIpMgmtWanAddrDynamic OBJECT IDENTIFIER ::= { saRgIpMgmtWanAddr 2 }

saRgIpMgmtWanAddrDynamicIp OBJECT-TYPE
    SYNTAX      IpAddress
    MAX-ACCESS  read-write
    STATUS      current
    DESCRIPTION
        "The IP address for the DHCP-assigned router address. This is the outside-facing WAN address of the router. Stored in non-vol, 0.0.0.0 after factory reset."
    ::= { saRgIpMgmtWanAddrDynamic 1 }

saRgIpMgmtWanAddrDynamicLeaseTime OBJECT-TYPE
    SYNTAX      Unsigned32
    UNITS       "seconds"
    MAX-ACCESS  read-write
    STATUS      current
    DESCRIPTION
            "The lease time for the dynamically assigned WAN address."
    DEFVAL { 3600 }
    ::= { saRgIpMgmtWanAddrDynamic 2 }

saRgIpMgmtWanAddrStatic OBJECT IDENTIFIER ::= { saRgIpMgmtWanAddr 3 }

saRgIpMgmtWanStaticNetwork OBJECT-TYPE
    SYNTAX      IpAddress
    MAX-ACCESS  read-write
    STATUS      current
    DESCRIPTION
        "Stored in non-vol, 0.0.0.0 after factory reset."
    ::= { saRgIpMgmtWanAddrStatic 1 }

saRgIpMgmtWanStaticSubnetMask OBJECT-TYPE
    SYNTAX      IpAddress
    MAX-ACCESS  read-write
    STATUS      current
    DESCRIPTION
        "Stored in non-vol, 0.0.0.0 after factory reset."
    ::= { saRgIpMgmtWanAddrStatic 2 }

saRgIpMgmtWanStaticGateway OBJECT-TYPE
    SYNTAX      IpAddress
    MAX-ACCESS  read-write
    STATUS      current
    DESCRIPTION
        "Stored in non-vol, 0.0.0.0 after factory reset."
    ::= { saRgIpMgmtWanAddrStatic 3 }

saRgIpMgmtWanStaticNameServerEnable OBJECT-TYPE
    SYNTAX TruthValue
    MAX-ACCESS read-write
    STATUS current
    DESCRIPTION
        "Defines whether static WAN DNS is enabled."
    ::= { saRgIpMgmtWanAddrStatic 4 }

saRgIpMgmtWanStaticHostName OBJECT-TYPE
    SYNTAX      SnmpAdminString
    MAX-ACCESS  read-write
    STATUS      current
    DESCRIPTION
        "This is the static host name of WAN."
    ::= { saRgIpMgmtWanAddrStatic 5 }

saRgIpMgmtWanStaticDomainName OBJECT-TYPE
    SYNTAX      SnmpAdminString
    MAX-ACCESS  read-write
    STATUS      current
    DESCRIPTION
        "This is the static domain name of WAN."
    ::= { saRgIpMgmtWanAddrStatic 6 }

saRgIpMgmtWanAddrDualIp OBJECT IDENTIFIER ::= { saRgIpMgmtWanAddr 4 }

saRgIpMgmtWanDualIpAddr OBJECT-TYPE
    SYNTAX      IpAddress
    MAX-ACCESS  read-only
    STATUS      current
    DESCRIPTION
        "IP address for the second IP stack.
         If not specified and saRgIpMgmtWanMode is set to
         dualIp(3), DHCP is used to acquire the IP address.
         Note: this object can only be set from config file."
    DEFVAL  { '00000000'h }
    ::= { saRgIpMgmtWanAddrDualIp 1 }

saRgIpMgmtWanDualIpRipAdvertised OBJECT-TYPE
    SYNTAX      TruthValue
    MAX-ACCESS  read-write
    STATUS      current
    DESCRIPTION
        "Specifies if the IP address is to be advertised in RIP,
         if RIP is enabled.
         Note: this object can only be set from config file."
    DEFVAL { true }
    ::= { saRgIpMgmtWanAddrDualIp 2 }

saRgIpMgmtWanAddrBackup OBJECT IDENTIFIER ::= { saRgIpMgmtWanAddr 5 }

saRgIpMgmtWanAddrBackupDefGw OBJECT-TYPE
    SYNTAX      IpAddress
    MAX-ACCESS  read-write
    STATUS      current
    DESCRIPTION
        "IP address for the default gateway that is used when the
         cable modem interface is offline. This object is not in
         effect when the cable modem is online.
         Note: this object is stored in non-vol and is 0.0.0.0
               after factory reset.
         The value of 0.0.0.0 means that this object is not in
         effect."
    ::= { saRgIpMgmtWanAddrBackup 1 }



saRgIpMgmtPassthrough OBJECT IDENTIFIER ::= { saRgIpMgmt 10 }

saRgIpMgmtPassthroughClientTable  OBJECT-TYPE
    SYNTAX      SEQUENCE OF SaRgIpMgmtPassthroughClientEntry
    MAX-ACCESS  not-accessible
    STATUS      current
    DESCRIPTION
        "A table of MAC addresses which represents stations that
         will be allowed to connect to the network bypassing any
         security, NAT and routing related settings. These
         stations are effectively behind bridged device."
    ::= { saRgIpMgmtPassthrough 1 }

saRgIpMgmtPassthroughClientEntry OBJECT-TYPE
    SYNTAX      SaRgIpMgmtPassthroughClientEntry
    MAX-ACCESS  not-accessible
    STATUS      current
    DESCRIPTION
        "A row in the table that specifies a single station MAC address."
    INDEX   { saRgIpMgmtPassthroughClientIndex }
    ::= { saRgIpMgmtPassthroughClientTable 1 }

SaRgIpMgmtPassthroughClientEntry ::=
    SEQUENCE    {
        saRgIpMgmtPassthroughClientIndex       INTEGER,
        saRgIpMgmtPassthroughClientRowStatus   RowStatus,
        saRgIpMgmtPassthroughClientMacAddress  MacAddress
    }

saRgIpMgmtPassthroughClientIndex OBJECT-TYPE
    SYNTAX      INTEGER (1..32)
    MAX-ACCESS  not-accessible
    STATUS      current
    DESCRIPTION
        "Indicates the instance of this table row."
    ::= { saRgIpMgmtPassthroughClientEntry 1 }

saRgIpMgmtPassthroughClientRowStatus OBJECT-TYPE
    SYNTAX      RowStatus
    MAX-ACCESS  read-write
    STATUS      current
    DESCRIPTION
        "The row status."
    ::= { saRgIpMgmtPassthroughClientEntry 2 }

saRgIpMgmtPassthroughClientMacAddress OBJECT-TYPE
    SYNTAX      MacAddress
    MAX-ACCESS  read-create
    STATUS      current
    DESCRIPTION
        "A MAC address of a station which will be allowed to connect
         directly to the network."
     ::= { saRgIpMgmtPassthroughClientEntry 3 }


saRgIpMgmtLanExtraSubnetTable OBJECT-TYPE
    SYNTAX SEQUENCE OF SaRgIpMgmtLanExtraSubnetEntry
    MAX-ACCESS not-accessible
    STATUS current
    DESCRIPTION
            "Additional IP addresses for primary LAN interface.
             If RIP is enabled, all subnets are advertised.
             All objects are stored in non-vol. The table
             is empty after factory reset."
    ::= { saRgIpMgmt 11 }

saRgIpMgmtLanExtraSubnetEntry OBJECT-TYPE
    SYNTAX      SaRgIpMgmtLanExtraSubnetEntry
    MAX-ACCESS  not-accessible
    STATUS     current
    DESCRIPTION
            "List of networks on the LAN side."
    INDEX { ifIndex }
    ::= { saRgIpMgmtLanExtraSubnetTable 1 }

SaRgIpMgmtLanExtraSubnetEntry ::= SEQUENCE {
    saRgIpMgmtLanExtraSubnetIndex      INTEGER,
    saRgIpMgmtLanExtraSubnetRowStatus  RowStatus,
    saRgIpMgmtLanExtraSubnetIpAddress  IpAddress,
    saRgIpMgmtLanExtraSubnetSubnetMask IpAddress,
    saRgIpMgmtLanExtraSubnetGateway    IpAddress
    }

saRgIpMgmtLanExtraSubnetIndex OBJECT-TYPE
    SYNTAX INTEGER
        {
        secondSubnet(1),
        thirdSubnet(2),
        fourthSubnet(3)
        }
    MAX-ACCESS  not-accessible
    STATUS      current
    DESCRIPTION
        "Indicates the instance of this table row."
    ::= { saRgIpMgmtLanExtraSubnetEntry 1 }

saRgIpMgmtLanExtraSubnetRowStatus OBJECT-TYPE
    SYNTAX      RowStatus
    MAX-ACCESS  read-write
    STATUS      current
    DESCRIPTION
        "The row status."
    ::= { saRgIpMgmtLanExtraSubnetEntry 2 }

saRgIpMgmtLanExtraSubnetIpAddress OBJECT-TYPE
    SYNTAX      IpAddress
    MAX-ACCESS  read-write
    STATUS      current
    DESCRIPTION
            ""
    ::= { saRgIpMgmtLanExtraSubnetEntry 3 }

saRgIpMgmtLanExtraSubnetSubnetMask OBJECT-TYPE
    SYNTAX      IpAddress
    MAX-ACCESS  read-write
    STATUS      current
    DESCRIPTION
            ""
    DEFVAL { 'ffffff00'h }    -- 255.255.255.0
    ::= { saRgIpMgmtLanExtraSubnetEntry 4 }

saRgIpMgmtLanExtraSubnetGateway OBJECT-TYPE
    SYNTAX      IpAddress
    MAX-ACCESS  read-write
    STATUS      current
    DESCRIPTION
            ""
    ::= { saRgIpMgmtLanExtraSubnetEntry 5 }

-- LT2P v2 settings

saRgIpMgmtL2tpClientTable OBJECT-TYPE
    SYNTAX SEQUENCE OF SaRgIpMgmtL2tpClientEntry
    MAX-ACCESS not-accessible
    STATUS obsolete
    DESCRIPTION
            "L2TP settings for a BSS when saRgIpMgmtLanMode
             is set to l2tp-client(3)."
    ::= { saRgIpMgmt 12 }

saRgIpMgmtL2tpClientEntry OBJECT-TYPE
    SYNTAX      SaRgIpMgmtL2tpClientEntry
    MAX-ACCESS  not-accessible
    STATUS     obsolete
    DESCRIPTION
            "The entry is available only when saRgIpMgmtLanMode is
             set to l2tp-client(3) for the specific ifIndex."
    INDEX { ifIndex }
    ::= { saRgIpMgmtL2tpClientTable 1 }

SaRgIpMgmtL2tpClientEntry ::= SEQUENCE {

    saRgIpMgmtL2tpClientServer      IpAddress,
    saRgIpMgmtL2tpClientPppUsername OCTET STRING,
    saRgIpMgmtL2tpClientPppPassword OCTET STRING
    }

saRgIpMgmtL2tpClientServer OBJECT-TYPE
    SYNTAX      IpAddress
    MAX-ACCESS  read-write
    STATUS      obsolete
    DESCRIPTION
            "IP address of the L2TP server."
    ::= { saRgIpMgmtL2tpClientEntry 1 }

saRgIpMgmtL2tpClientPppUsername OBJECT-TYPE
    SYNTAX      OCTET STRING (SIZE(0..32))
    MAX-ACCESS  read-write
    STATUS      obsolete
    DESCRIPTION
            ""
    ::= { saRgIpMgmtL2tpClientEntry 2 }

saRgIpMgmtL2tpClientPppPassword OBJECT-TYPE
    SYNTAX      OCTET STRING (SIZE(0..32))
    MAX-ACCESS  read-write
    STATUS      obsolete
    DESCRIPTION
            ""
    ::= { saRgIpMgmtL2tpClientEntry 3 }

-- **********************
-- LAN PORT Control Table
-- **********************
saRgIpMgmtLanPortControl   OBJECT IDENTIFIER ::=  { saRgIpMgmt 13 }


saRgIpMgmtLanPortControlTable OBJECT-TYPE
       SYNTAX      SEQUENCE OF SaRgIpMgmtLanPortControlEntry
       MAX-ACCESS  not-accessible
       STATUS      current
       DESCRIPTION
               "Table to control the mode for each LAN PORT.
               LAN PORTs are numbered 1-4 and are mapped to physical
               port location. Each port can either be in router or
               in bridge mode."
    ::= { saRgIpMgmtLanPortControl 1 }

saRgIpMgmtLanPortControlEntry OBJECT-TYPE
    SYNTAX      SaRgIpMgmtLanPortControlEntry
    MAX-ACCESS  not-accessible
    STATUS      current
    DESCRIPTION
            ""
    INDEX { saRgIpMgmtLanPortControlIndex }
    ::= { saRgIpMgmtLanPortControlTable 1 }

SaRgIpMgmtLanPortControlEntry ::= SEQUENCE {
    saRgIpMgmtLanPortControlIndex       INTEGER,
    saRgIpMgmtLanPortMode               INTEGER
    }

saRgIpMgmtLanPortControlIndex OBJECT-TYPE
    SYNTAX      INTEGER (1..4)
    MAX-ACCESS  not-accessible
    STATUS      current
    DESCRIPTION
            "The index for each LAN port"
    ::= { saRgIpMgmtLanPortControlEntry 1 }

saRgIpMgmtLanPortMode OBJECT-TYPE
    SYNTAX  INTEGER {
            bridge (1),
            router (2)
            }
    MAX-ACCESS  read-write
    STATUS      current
    DESCRIPTION
            "Each physical LAN port can either be controlled
            as bridge or router. The saRgIpMgmtLanPortMode MIB only works
            when SaRgIpMgmtLanMode.32=4(Mixed). Setting this MIB
            through SNMP will take effect only after
            saRgIpMgmtApplySettings.0 set to true and this setting will
            reboot to take effect"
    ::= { saRgIpMgmtLanPortControlEntry 2 }

saRgIpMgmtRestoreDefaults OBJECT-TYPE
   SYNTAX INTEGER {
                        disable(0),
                        bridgeDefaults(1),
                        routerDefaults(2)
                        }
   MAX-ACCESS read-write
   STATUS current
   DESCRIPTION
                "MIB to control the default behavior for LAN mode.
                NOTE: This is customer specific ONLY. Not available in GA yet
                Default behavior is disabled (0). - This means that GA behavior is the normal behavior.
                bridgeDefaults(1) - All the MIB objects in bridgeDefaults group would be set when CM boots up and would be retained across reboots/factory reset
                routerDefaults(2) - All the MIB objects in routerDefaults group would be set when CM boots up and would be retained across reboots/factory reset"
  DEFVAL { 0 }

  ::= { saRgIpMgmt 14 }

--====================================================================
--
--    saRgIpMgmtLanAddrIpv6Table (CDP Ipv6 Address Table)
--
--    The saRgIpMgmtLanAddrUpv6Table contains the Ipv6 parameters
--   
--
--=========================================================================

saRgIpMgmtLanAddrIpv6Table OBJECT-TYPE
       SYNTAX      SEQUENCE OF SaRgIpMgmtLanAddrIpv6Entry
       MAX-ACCESS  not-accessible
       STATUS      current
       DESCRIPTION
               "IP addresses of devices served by DHCPv6/SLAAC"
    ::= { saRgIpMgmt 15 }

saRgIpMgmtLanAddrIpv6Entry OBJECT-TYPE
    SYNTAX      SaRgIpMgmtLanAddrIpv6Entry
    MAX-ACCESS  not-accessible
    STATUS      current
    DESCRIPTION
            "List of general parameters pertaining to LAN-Trans IP
            address reservations and leases."
    INDEX { ifIndex, saRgIpMgmtLanAddrIpv6Index }
    ::= { saRgIpMgmtLanAddrIpv6Table 1 }

SaRgIpMgmtLanAddrIpv6Entry ::= SEQUENCE {
    saRgIpMgmtLanAddrIpv6Index              INTEGER,
    saRgIpMgmtLanAddrIpv6Ip                 InetAddress,
    saRgIpMgmtLanAddrIpv6PhysAddr           PhysAddress,
    saRgIpMgmtLanAddrIpv6Status				DateAndTime,
    saRgIpMgmtLanAddrIpv6Method		   	    SnmpAdminString,
    saRgIpMgmtLanAddrIpv6ClientId           SnmpAdminString,
    saRgIpMgmtLanAddrIpv6Interface          SnmpAdminString,
    saRgIpMgmtLanAddrIpv6CpeStatus          INTEGER
    }

saRgIpMgmtLanAddrIpv6Index OBJECT-TYPE
    SYNTAX      INTEGER
    MAX-ACCESS  not-accessible
    STATUS      current
    DESCRIPTION
            "The index of the the LAN IPv6 Device in the LAN-Trans Realm."
    ::= { saRgIpMgmtLanAddrIpv6Entry 1 }

saRgIpMgmtLanAddrIpv6Ip OBJECT-TYPE
    SYNTAX      InetAddress
    MAX-ACCESS  read-only
    STATUS      current
    DESCRIPTION
            ""
    ::= { saRgIpMgmtLanAddrIpv6Entry 3 }

saRgIpMgmtLanAddrIpv6PhysAddr OBJECT-TYPE
    SYNTAX      PhysAddress
    MAX-ACCESS  read-only
    STATUS      current
    DESCRIPTION
            "The client's (i.e., LAN IP Device's) hardware address as
            indicated in the chaddr field of its DHCP REQUEST message."
    ::= { saRgIpMgmtLanAddrIpv6Entry 4 }

saRgIpMgmtLanAddrIpv6Status OBJECT-TYPE
    SYNTAX      SnmpAdminString
    MAX-ACCESS  read-only
    STATUS      current
    DESCRIPTION
            "Ipv6 Reachability state the device."
    ::= { saRgIpMgmtLanAddrIpv6Entry 5 }

saRgIpMgmtLanAddrIpv6Method OBJECT-TYPE
    SYNTAX      SnmpAdminString
    MAX-ACCESS  read-only
    STATUS      current
    DESCRIPTION
            "This is the method how IPv6 address was obtained SLAAC or DHCPv6."
    ::= { saRgIpMgmtLanAddrIpv6Entry 6 }

saRgIpMgmtLanAddrIpv6ClientId OBJECT-TYPE
    SYNTAX      SnmpAdminString
    MAX-ACCESS  read-only
    STATUS      current
    DESCRIPTION
            "This is the Client Class Identifier, based on DHCP option 60."
    ::= { saRgIpMgmtLanAddrIpv6Entry 7 }

saRgIpMgmtLanAddrIpv6Interface OBJECT-TYPE
    SYNTAX      SnmpAdminString
    MAX-ACCESS  read-only
    STATUS      current
    DESCRIPTION
            "This will show the associated interface (LAN, WiFi or MoCA) of the connected CPE."
    ::= { saRgIpMgmtLanAddrIpv6Entry 8 }

saRgIpMgmtLanAddrIpv6CpeStatus OBJECT-TYPE
    SYNTAX INTEGER {
        offline(0),
        online(1)
        }
    MAX-ACCESS    read-only
    STATUS        current
    DESCRIPTION
        "This MIB shows the client's current online status.
                - 0 - The client currently has no connectivity.
                - 1 - The client currently has connectivity and is online.
                "
    DEFVAL { 0 }
    ::= { saRgIpMgmtLanAddrIpv6Entry 9 }



-- Apply setting to activate chagnes:
saRgIpMgmtApplySettings OBJECT-TYPE
    SYNTAX      TruthValue
    MAX-ACCESS  read-write
    STATUS      current
    DESCRIPTION
        "If set to true(1), then all the settings (MIB values)
         from this MIB tree will be applied to run time configuration,
         modifying previous RG operation with the new settings.
         Before setting the value to true, MIBs modified in the MIB
         tree are stored in non-vol and will not modify RG operation
         until saRgIpMgmtApplySettings is set to true or CM resets.
         Note: this applies only to the MIB objects that are stored
         in non-vol.
         Always returns false(2) when read."
    ::= { saRgIpMgmt 1001 }



-- =============================================
-- FIREWALL
--
-- Also includes port tiggering, forwarding, DMZ
-- =============================================

saRgFirewall OBJECT IDENTIFIER ::=  { saRg 4 }

saRgFirewallBase OBJECT IDENTIFIER ::=  { saRgFirewall 1 }

saRgFirewallProtection OBJECT-TYPE
SYNTAX INTEGER {
disable(0),
low(1),
medium (2),
high (3),
custom (4)
}
MAX-ACCESS read-write
STATUS current
DESCRIPTION
"Controls the firewall. This parameter is stored in non-vol and
is enabled after factory reset.
Disable: Completely disables the SPI Firewall
Low/ Enable: Is Equivalent to Old Firewall Enable Mode with No Ports Restricted
Medium: Enables the SPI Firewall plus includes a list of Allowed Services that will be allowed to through the Firewall
High: Enables the SPI Firewall plus a shortened list of Allowed Services
Custom: Enables the SPI Firewall set to custom values. For use with Puma-based products."
::= { saRgFirewallBase 1 }

saRgFirewallDmzAddress OBJECT-TYPE
    SYNTAX      IpAddress
    MAX-ACCESS  read-write
    STATUS      current
    DESCRIPTION
            "Stored in non-vol, 0.0.0.0 after facroty reset."
    ::= { saRgFirewallBase 2 }

saRgFirewallPortForwardEnable OBJECT-TYPE
    SYNTAX      TruthValue
    MAX-ACCESS  read-write
    STATUS      current
    DESCRIPTION
        "Enables or disables firewall port forwarding on the device."
    DEFVAL { false }
    ::= { saRgFirewallBase 3 }

saRgFirewallPortTriggerEnable OBJECT-TYPE
    SYNTAX      TruthValue
    MAX-ACCESS  read-write
    STATUS      current
    DESCRIPTION
        "Enables or disables firewall port triggering on the device."
    DEFVAL { false }
    ::= { saRgFirewallBase 4 }

        saRgFirewallTraffic OBJECT IDENTIFIER ::=  { saRgFirewall 2 }

saRgFirewallTrafficBlock OBJECT-TYPE
    SYNTAX BITS {
        proxy(0),
        cookies(1),
        javaApplets(2),
        activeX(3),
        popUp(4),
        fragmentedIp(5)
    }
    MAX-ACCESS    read-write
    STATUS        current
    DESCRIPTION
        "Controls blocking of certain traffic.
         Stored in non-vol, 0x00 after factory reset.
        Note: For DOCSIS 3.0 products with 553 and newer SW,
        proxy(0), cookies(1), javaApplets(2), activeX(3), popUp(4) are NOT Supported."
    ::= { saRgFirewallTraffic 1 }

saRgFirewallTrafficDetect OBJECT-TYPE
    SYNTAX BITS {
        portScan(0),
        ipFlood(1)
    }
    MAX-ACCESS    read-write
    STATUS        current
    DESCRIPTION
        "Controls detecting of certain traffic.
         Stored in non-vol, 0x40 after factory reset."
    ::= { saRgFirewallTraffic 2 }

saRgFirewallTrafficPassThru OBJECT-TYPE
    SYNTAX BITS {
        ipsec(0),
        pptp(1),
        multicast(2),
        ident(3),
        icmp(4)
    }
    MAX-ACCESS    read-write
    STATUS        current
    DESCRIPTION
        "Controls passthru for certain traffic:
                ipsec(0), Block IPSec
                pptp(1), Block PPTP
                multicast(2), Block Multicast
                ident(3), Block IDENT (port 113), for use with Puma-based products
                icmp(4), Block ICMP, for use with Puma-based products
        Stored in non-vol, 0xe0 after factory reset."
    ::= { saRgFirewallTraffic 3 }

saRgFirewallWANBlockingEnable OBJECT-TYPE
    SYNTAX TruthValue
    MAX-ACCESS  read-write
    STATUS      current
    DESCRIPTION
        "Controls WAN blocking RG feature.
         Stored in non-vol, enabled after factory reset."
    ::= { saRgFirewallTraffic 4 }

saRgFirewallIpv6Protection OBJECT-TYPE
	SYNTAX INTEGER {
		disable(0),
		enable(1)				
	}
	MAX-ACCESS read-write
	STATUS current
	DESCRIPTION
		"Controls the IPv6 firewall. This parameter is stored in non-vol and
		is enabled after factory reset.
		Disable: Completely disables the IPv6 Firewall
		Enable: Enable firewall for IPv6 traffic."
	DEFVAL { 1 }
	::= { saRgFirewallBase 5 }


-- Firewall events reporting

saRgFirewallReport OBJECT IDENTIFIER ::=  { saRgFirewall 4 }

saRgFirewallReportEventTable OBJECT-TYPE
       SYNTAX      SEQUENCE OF SaRgFirewallReportEventEntry
       MAX-ACCESS  not-accessible
       STATUS      current
       DESCRIPTION
               "This table is stored in non-vol and is empty
                after factory reset."
    ::= { saRgFirewallReport 1 }

saRgFirewallReportEventEntry OBJECT-TYPE
    SYNTAX      SaRgFirewallReportEventEntry
    MAX-ACCESS  not-accessible
    STATUS      current
    DESCRIPTION
            ""
    INDEX { saRgFirewallReportEventIndex }
    ::= { saRgFirewallReportEventTable 1 }

SaRgFirewallReportEventEntry ::= SEQUENCE {
    saRgFirewallReportEventIndex          INTEGER,
    saRgFirewallReportEventDescription    SnmpAdminString,
    saRgFirewallReportEventCount          INTEGER,
    saRgFirewallReportEventLastOccurance  SnmpAdminString,
    saRgFirewallReportEventTarget         SnmpAdminString,
    saRgFirewallReportEventSource         SnmpAdminString
    }

saRgFirewallReportEventIndex OBJECT-TYPE
    SYNTAX      INTEGER
    MAX-ACCESS  not-accessible
    STATUS      current
    DESCRIPTION
            "The index"
    ::= { saRgFirewallReportEventEntry 1 }

saRgFirewallReportEventDescription OBJECT-TYPE
    SYNTAX      SnmpAdminString
    MAX-ACCESS  read-only
    STATUS      current
    DESCRIPTION
            ""
    ::= { saRgFirewallReportEventEntry 2 }

saRgFirewallReportEventCount OBJECT-TYPE
    SYNTAX      INTEGER
    MAX-ACCESS  read-only
    STATUS      current
    DESCRIPTION
            ""
    ::= { saRgFirewallReportEventEntry 3 }

saRgFirewallReportEventLastOccurance OBJECT-TYPE
    SYNTAX      SnmpAdminString
    MAX-ACCESS  read-only
    STATUS      current
    DESCRIPTION
            ""
    ::= { saRgFirewallReportEventEntry 4 }

saRgFirewallReportEventTarget OBJECT-TYPE
    SYNTAX      SnmpAdminString
    MAX-ACCESS  read-only
    STATUS      current
    DESCRIPTION
            ""
    ::= { saRgFirewallReportEventEntry 5 }

saRgFirewallReportEventSource OBJECT-TYPE
    SYNTAX      SnmpAdminString
    MAX-ACCESS  read-only
    STATUS      current
    DESCRIPTION
            ""
    ::= { saRgFirewallReportEventEntry 6 }


saRgFirewallReportMgmt OBJECT IDENTIFIER ::=  { saRgFirewallReport 2 }

saRgFirewallReportMgmtClearLog OBJECT-TYPE
    SYNTAX TruthValue
    MAX-ACCESS    read-write
    STATUS        current
    DESCRIPTION
        "Note: this object does not need saRgFirewallApplySettings
         to take effect."
    DEFVAL { false }
    ::= { saRgFirewallReportMgmt 1 }

saRgFirewallReportEmailLogNow OBJECT-TYPE
    SYNTAX TruthValue
    MAX-ACCESS    read-write
    STATUS        current
    DESCRIPTION
        "Triggers sending currect logs via email. Always returns false.
         Note: this objects does not need saRgFirewallApplySettings to
         send the logs."
    DEFVAL { false }
    ::= { saRgFirewallReportMgmt 2 }


saRgFirewallReportEmail OBJECT IDENTIFIER ::=  { saRgFirewallReport 3 }

saRgFirewallReportEmailEnable OBJECT-TYPE
    SYNTAX TruthValue
    MAX-ACCESS    read-write
    STATUS        current
    DESCRIPTION
        "Enables sending logs via email. Email is sent when an event happens."
    ::= { saRgFirewallReportEmail 1 }

saRgFirewallReportEmailAddress OBJECT-TYPE
    SYNTAX SnmpAdminString
    MAX-ACCESS    read-write
    STATUS        current
    DESCRIPTION
        "This is stored in non-vol and is empty after factory reset."
    ::= { saRgFirewallReportEmail 2 }

saRgFirewallReportEmailSmtpServer OBJECT-TYPE
    SYNTAX SnmpAdminString
    MAX-ACCESS    read-write
    STATUS        current
    DESCRIPTION
        "IP address or FQDN.
         Stored in non-vol. Empty after factory reset."
    ::= { saRgFirewallReportEmail 3 }

saRgFirewallReportEmailUsername OBJECT-TYPE
    SYNTAX SnmpAdminString
    MAX-ACCESS    read-write
    STATUS        current
    DESCRIPTION
        "This is stored in non-vol and is empty after factory reset."
    ::= { saRgFirewallReportEmail 4 }

saRgFirewallReportEmailPassword OBJECT-TYPE
    SYNTAX SnmpAdminString
    MAX-ACCESS    read-write
    STATUS        current
    DESCRIPTION
        "This is stored in non-vol and is empty after factory reset."
    ::= { saRgFirewallReportEmail 5 }


-- Firewall IP filtering

saRgFirewallRules OBJECT IDENTIFIER ::=  { saRgFirewall 5 }

saRgFirewallIpFilterTable OBJECT-TYPE
       SYNTAX      SEQUENCE OF SaRgFirewallIpFilterEntry
       MAX-ACCESS  not-accessible
       STATUS      current
       DESCRIPTION
               "This table is stored in non-vol and is empty
                after factory reset."
    ::= { saRgFirewallRules 1 }

saRgFirewallIpFilterEntry OBJECT-TYPE
    SYNTAX      SaRgFirewallIpFilterEntry
    MAX-ACCESS  not-accessible
    STATUS      current
    DESCRIPTION
            ""
    INDEX { saRgFirewallIpFilterIndex }
    ::= { saRgFirewallIpFilterTable 1 }

SaRgFirewallIpFilterEntry ::= SEQUENCE {
    saRgFirewallIpFilterIndex              INTEGER,
    saRgFirewallIpFilterRowStatus          RowStatus,
    saRgFirewallIpFilterAddressStart       IpAddress,
    saRgFirewallIpFilterAddressEnd         IpAddress,
    saRgFirewallIpFilterTrusted            INTEGER,
    saRgFirewallIpFilterPolicy             INTEGER
    }

saRgFirewallIpFilterIndex OBJECT-TYPE
    SYNTAX      INTEGER (1..10)
    MAX-ACCESS  not-accessible
    STATUS      current
    DESCRIPTION
            "The index"
    ::= { saRgFirewallIpFilterEntry 1 }

saRgFirewallIpFilterRowStatus OBJECT-TYPE
    SYNTAX      RowStatus
    MAX-ACCESS  read-write
    STATUS      current
    DESCRIPTION
            "The row status. A row can be destroyed.
             If the row is not used, set to notInService."
    ::= { saRgFirewallIpFilterEntry 2 }

saRgFirewallIpFilterAddressStart OBJECT-TYPE
    SYNTAX      IpAddress
    MAX-ACCESS  read-write
    STATUS      current
    DESCRIPTION
            ""
    ::= { saRgFirewallIpFilterEntry 3 }

saRgFirewallIpFilterAddressEnd OBJECT-TYPE
    SYNTAX      IpAddress
    MAX-ACCESS  read-write
    STATUS      current
    DESCRIPTION
            ""
    ::= { saRgFirewallIpFilterEntry 4 }

saRgFirewallIpFilterTrusted OBJECT-TYPE
    SYNTAX      INTEGER {
        block(1),
        permit(2)
    }
    MAX-ACCESS  read-write
    STATUS      current
    DESCRIPTION
            "Block/Permit this IP address based on saRgFirewallIpFilterPolicy"
    DEFVAL { block }
    ::= { saRgFirewallIpFilterEntry 5 }

saRgFirewallIpFilterPolicy OBJECT-TYPE
    SYNTAX      INTEGER {
        urlkeyword(1),
        port(2),
                none(3)
    }
    MAX-ACCESS  read-write
    STATUS      current
    DESCRIPTION
            "If urlkeyword(1), saRgFirewallIpFilterTrusted can be set to permit a particular computer regardless of saRgFirewallUrlKeywordFilterTable rules
            If port(2), saRgFirewallIpFilterTrusted can be set to permit a particular computer regardless of saRgFirewallPortFilterTable rules
                If none(3), saRgFirewallIpFilterTrusted can be set to block or permit a computer regardless of any existing rules"
    DEFVAL { none }
    ::= { saRgFirewallIpFilterEntry 6 }

saRgFirewallPortFilterTable OBJECT-TYPE
       SYNTAX      SEQUENCE OF SaRgFirewallPortFilterEntry
       MAX-ACCESS  not-accessible
       STATUS      current
       DESCRIPTION
               "This table is stored in non-vol and is empty
                after factory reset."
    ::= { saRgFirewallRules 2 }

saRgFirewallPortFilterEntry OBJECT-TYPE
    SYNTAX      SaRgFirewallPortFilterEntry
    MAX-ACCESS  not-accessible
    STATUS      current
    DESCRIPTION
            ""
    INDEX { saRgFirewallPortFilterIndex }
    ::= { saRgFirewallPortFilterTable 1 }

SaRgFirewallPortFilterEntry ::= SEQUENCE {
    saRgFirewallPortFilterIndex              INTEGER,
    saRgFirewallPortFilterRowStatus          RowStatus,
    saRgFirewallPortFilterPortStart          InetPortNumber,
    saRgFirewallPortFilterPortEnd            InetPortNumber,
    saRgFirewallPortFilterProto              INTEGER,
    saRgFirewallPortFilterAlwaysBlock        TruthValue,
    saRgFirewallPortFilterBlockStartTime     OCTET STRING,
    saRgFirewallPortFilterBlockEndTime       OCTET STRING,
    saRgFirewallPortFilterBlockDays          BITS
    }

saRgFirewallPortFilterIndex OBJECT-TYPE
    SYNTAX      INTEGER (1..10)
    MAX-ACCESS  not-accessible
    STATUS      current
    DESCRIPTION
            "The index"
    ::= { saRgFirewallPortFilterEntry 1 }

saRgFirewallPortFilterRowStatus OBJECT-TYPE
    SYNTAX      RowStatus
    MAX-ACCESS  read-write
    STATUS      current
    DESCRIPTION
            "The row status. A row can be destroyed.
             If the row is not used, set to notInService."
    ::= { saRgFirewallPortFilterEntry 2 }

saRgFirewallPortFilterPortStart OBJECT-TYPE
    SYNTAX      InetPortNumber
    MAX-ACCESS  read-write
    STATUS      current
    DESCRIPTION
            ""
    ::= { saRgFirewallPortFilterEntry 5 }

saRgFirewallPortFilterPortEnd OBJECT-TYPE
    SYNTAX      InetPortNumber
    MAX-ACCESS  read-write
    STATUS      current
    DESCRIPTION
            ""
    ::= { saRgFirewallPortFilterEntry 6 }

saRgFirewallPortFilterProto OBJECT-TYPE
    SYNTAX  INTEGER {
        udp(1),
        tcp(2),
        udpTcp(3)
        }
    MAX-ACCESS  read-write
    STATUS      current
    DESCRIPTION
            "IP protocol to block."
    DEFVAL { 3 }
    ::= { saRgFirewallPortFilterEntry 7 }

saRgFirewallPortFilterAlwaysBlock OBJECT-TYPE
    SYNTAX      TruthValue
    MAX-ACCESS  read-write
    STATUS      current
    DESCRIPTION
        "If True(1), always be blocked, regardless of startTime, endTime and blockDays
        If False(2), blocked at time set in startTime, endTime and blockDays"
    DEFVAL { true }
    ::= { saRgFirewallPortFilterEntry 8 }

saRgFirewallPortFilterBlockStartTime OBJECT-TYPE
    SYNTAX      OCTET STRING (SIZE (5))
    MAX-ACCESS  read-write
    STATUS      current
    DESCRIPTION
        "24 Hour format HH:MM to set the start time to block"
    ::= { saRgFirewallPortFilterEntry 9 }

saRgFirewallPortFilterBlockEndTime OBJECT-TYPE
    SYNTAX      OCTET STRING (SIZE (5))
    MAX-ACCESS  read-write
    STATUS      current
    DESCRIPTION
        "24 Hour format HH:MM to set the end time to block"
    ::= { saRgFirewallPortFilterEntry 10 }

saRgFirewallPortFilterBlockDays OBJECT-TYPE
    SYNTAX      BITS {
        sun(0),
        mon(1),
        tue(2),
        wed(3),
        thu(4),
        fri(5),
        sat(6)
        }
    MAX-ACCESS  read-write
    STATUS      current
    DESCRIPTION
        "BITMAP to indicate which days to block"
    ::= { saRgFirewallPortFilterEntry 11 }
saRgFirewallMacFilterTable  OBJECT-TYPE
    SYNTAX      SEQUENCE OF SaRgFirewallMacFilterEntry
    MAX-ACCESS  not-accessible
    STATUS      current
    DESCRIPTION
        "A table of clients MAC addresses that are denied from accessing Internet."
    ::= { saRgFirewallRules 3 }

saRgFirewallMacFilterEntry OBJECT-TYPE
    SYNTAX      SaRgFirewallMacFilterEntry
    MAX-ACCESS  not-accessible
    STATUS      current
    DESCRIPTION
        "A row in the table that specifies a single station MAC address."
    INDEX   { saRgFirewallMacFilterIndex }
    ::= { saRgFirewallMacFilterTable 1 }

SaRgFirewallMacFilterEntry ::=
    SEQUENCE    {
            saRgFirewallMacFilterIndex              INTEGER,
            saRgFirewallMacFilterRowStatus          RowStatus,
            saRgFirewallMacFilterAddress          MacAddress,
            saRgFirewallMacFilterAlwaysBlock      TruthValue,
            saRgFirewallMacFilterBlockStartTime   OCTET STRING,
            saRgFirewallMacFilterBlockEndTime     OCTET STRING,
            saRgFirewallMacFilterBlockDays        BITS
    }

saRgFirewallMacFilterIndex OBJECT-TYPE
    SYNTAX      INTEGER (1..20)
    MAX-ACCESS  not-accessible
    STATUS      current
    DESCRIPTION
            "The index"
    ::= { saRgFirewallMacFilterEntry 1 }

saRgFirewallMacFilterRowStatus OBJECT-TYPE
    SYNTAX      RowStatus
    MAX-ACCESS  read-write
    STATUS      current
    DESCRIPTION
            "The row status. A row can be destroyed.
             If the row is not used, set to notInService."
    ::= { saRgFirewallMacFilterEntry 2 }

saRgFirewallMacFilterAddress OBJECT-TYPE
    SYNTAX      MacAddress
    MAX-ACCESS  read-write
    STATUS      current
    DESCRIPTION
        "A MAC address of a station that cannot access Internet."
    ::= { saRgFirewallMacFilterEntry 3 }

saRgFirewallMacFilterAlwaysBlock OBJECT-TYPE
    SYNTAX      TruthValue
    MAX-ACCESS  read-write
    STATUS      current
    DESCRIPTION
        "If true(1), always be blocked/permitted, regardless of startTime, endTime and blockDays
        If false(2), blocked/permitted at time set in startTime, endTime and blockDays"
    DEFVAL { true }
    ::= { saRgFirewallMacFilterEntry 4 }

saRgFirewallMacFilterBlockStartTime OBJECT-TYPE
    SYNTAX      OCTET STRING (SIZE (5))
    MAX-ACCESS  read-write
    STATUS      current
    DESCRIPTION
        "24 Hour format HH:MM to set the start time to block/permit"
    ::= { saRgFirewallMacFilterEntry 5 }

saRgFirewallMacFilterBlockEndTime OBJECT-TYPE
    SYNTAX      OCTET STRING (SIZE (5))
    MAX-ACCESS  read-write
    STATUS      current
    DESCRIPTION
        "24 Hour format HH:MM to set the end time to block/permit"
    ::= { saRgFirewallMacFilterEntry 6 }

saRgFirewallMacFilterBlockDays OBJECT-TYPE
    SYNTAX      BITS {
        sun(0),
        mon(1),
        tue(2),
        wed(3),
        thu(4),
        fri(5),
        sat(6)
        }
    MAX-ACCESS  read-write
    STATUS      current
    DESCRIPTION
        "BITMAP to indicate which days to block/permit"
    ::= { saRgFirewallMacFilterEntry 7 }

saRgFirewallMacFilterEnable OBJECT-TYPE
    SYNTAX      TruthValue
    MAX-ACCESS  read-write
    STATUS      current
    DESCRIPTION
        "True = Enable the Mac address filtering feature. False = disable.
        this Value is written to non-vol and set to false after a factory reset."
    DEFVAL { false }
    ::= { saRgFirewallRules 4 }

saRgFirewallMacFilterMode OBJECT-TYPE
    SYNTAX      INTEGER {
        block(0),
        permit(1)
        }
    MAX-ACCESS  read-write
    STATUS      current
    DESCRIPTION
        "block(0)- Macs listed in the saRgFirewallMacFilterEntryTable will be blocked.
        permit(1)- Macs listed in the saRgFirewallMacFilterEntryTable will be permitted.
        This value is written to non-vol and is set to block(0) after a factory reset."
    DEFVAL { 0 }
    ::= { saRgFirewallRules 5 }

saRgFirewallPortFilterEnable OBJECT-TYPE
    SYNTAX      TruthValue
    MAX-ACCESS  read-write
    STATUS      current
    DESCRIPTION
        "True = Enable the Port filtering feature. False = disable.
        this Value is written to non-vol and set to false after a factory reset."
    DEFVAL { false }
    ::= { saRgFirewallRules 6 }

saRgFirewallUrlKeywordFiltering   OBJECT IDENTIFIER ::=  { saRgFirewallRules 7 }

saRgFirewallUrlKeywordFilterEnable OBJECT-TYPE
    SYNTAX      TruthValue
    MAX-ACCESS  read-write
    STATUS      current
    DESCRIPTION
        "True = Enable the Url Keyword filtering feature. False = disable.
        this Value is written to non-vol and set to false after a factory reset."
    DEFVAL { false }
    ::= { saRgFirewallUrlKeywordFiltering 1 }

saRgFirewallUrlKeywordFilterTable  OBJECT-TYPE
    SYNTAX      SEQUENCE OF SaRgFirewallUrlKeywordFilterEntry
    MAX-ACCESS  not-accessible
    STATUS      current
    DESCRIPTION
        "A table of url and keyword rules that are denied from accessing Internet."
    ::= { saRgFirewallUrlKeywordFiltering 2 }

saRgFirewallUrlKeywordFilterEntry OBJECT-TYPE
    SYNTAX      SaRgFirewallUrlKeywordFilterEntry
    MAX-ACCESS  not-accessible
    STATUS      current
    DESCRIPTION
        "A row in the table that specifies a single station MAC address."
    INDEX   { saRgFirewallUrlKeywordFilterIndex }
    ::= { saRgFirewallUrlKeywordFilterTable 1 }

SaRgFirewallUrlKeywordFilterEntry ::=
    SEQUENCE    {
            saRgFirewallUrlKeywordFilterIndex            INTEGER,
            saRgFirewallUrlKeywordFilterRowStatus        RowStatus,
            saRgFirewallUrlKeywordFilterMethod           INTEGER,
            saRgFirewallUrlKeywordFilterMatch            OCTET STRING,
            saRgFirewallUrlKeywordFilterAlwaysBlock      TruthValue,
            saRgFirewallUrlKeywordFilterBlockStartTime   OCTET STRING,
            saRgFirewallUrlKeywordFilterBlockEndTime     OCTET STRING,
            saRgFirewallUrlKeywordFilterBlockDays        BITS
    }

saRgFirewallUrlKeywordFilterIndex OBJECT-TYPE
    SYNTAX      INTEGER (1..20)
    MAX-ACCESS  not-accessible
    STATUS      current
    DESCRIPTION
            "The index"
    ::= { saRgFirewallUrlKeywordFilterEntry 1 }

saRgFirewallUrlKeywordFilterRowStatus OBJECT-TYPE
    SYNTAX      RowStatus
    MAX-ACCESS  read-write
    STATUS      current
    DESCRIPTION
            "The row status. A row can be destroyed.
             If the row is not used, set to notInService."
    ::= { saRgFirewallUrlKeywordFilterEntry 2 }

saRgFirewallUrlKeywordFilterMethod OBJECT-TYPE
    SYNTAX      INTEGER {
                url(1),
                keyword(2)
        }
    MAX-ACCESS  read-write
    STATUS      current
    DESCRIPTION
        "If url(1),deny access to specific websites (URLs)
        If keyword(2), deny access to websites containing specific words"
    ::= { saRgFirewallUrlKeywordFilterEntry 3 }

saRgFirewallUrlKeywordFilterMatch OBJECT-TYPE
    SYNTAX      OCTET STRING
    MAX-ACCESS  read-write
    STATUS      current
    DESCRIPTION
        "URLs or specific words according to Method set"
    ::= { saRgFirewallUrlKeywordFilterEntry 4 }

saRgFirewallUrlKeywordFilterAlwaysBlock OBJECT-TYPE
    SYNTAX      TruthValue
    MAX-ACCESS  read-write
    STATUS      current
    DESCRIPTION
        "If true(1), always be blocked, regardless of startTime, endTime and blockDays
        If false(2), blocked at time set in startTime, endTime and blockDays"
    DEFVAL { true }
    ::= { saRgFirewallUrlKeywordFilterEntry 5 }

saRgFirewallUrlKeywordFilterBlockStartTime OBJECT-TYPE
    SYNTAX      OCTET STRING (SIZE (5))
    MAX-ACCESS  read-write
    STATUS      current
    DESCRIPTION
        "24 Hour format HH:MM to set the start time to block"
    ::= { saRgFirewallUrlKeywordFilterEntry 6 }

saRgFirewallUrlKeywordFilterBlockEndTime OBJECT-TYPE
    SYNTAX      OCTET STRING (SIZE (5))
    MAX-ACCESS  read-write
    STATUS      current
    DESCRIPTION
        "24 Hour format HH:MM to set the end time to block"
    ::= { saRgFirewallUrlKeywordFilterEntry 7 }

saRgFirewallUrlKeywordFilterBlockDays OBJECT-TYPE
    SYNTAX      BITS {
        sun(0),
        mon(1),
        tue(2),
        wed(3),
        thu(4),
        fri(5),
        sat(6)
        }
    MAX-ACCESS  read-write
    STATUS      current
    DESCRIPTION
        "BITMAP to indicate which days to block"
    ::= { saRgFirewallUrlKeywordFilterEntry 8 }

-- Port forwarding

saRgFirewallPortFwdTable OBJECT-TYPE
       SYNTAX      SEQUENCE OF SaRgFirewallPortFwdEntry
       MAX-ACCESS  not-accessible
       STATUS      current
       DESCRIPTION
               "This table is stored in non-vol and is empty
                after factory reset."
    ::= { saRgFirewall 6 }

saRgFirewallPortFwdEntry OBJECT-TYPE
    SYNTAX      SaRgFirewallPortFwdEntry
    MAX-ACCESS  not-accessible
    STATUS      current
    DESCRIPTION
            ""
    INDEX { saRgFirewallPortFwdIndex }
    ::= { saRgFirewallPortFwdTable 1 }

SaRgFirewallPortFwdEntry ::= SEQUENCE {
    saRgFirewallPortFwdIndex              INTEGER,
    saRgFirewallPortFwdRowStatus          RowStatus,
    saRgFirewallPortFwdToAddress          IpAddress,
    saRgFirewallPortFwdPortStart          InetPortNumber,
    saRgFirewallPortFwdPortEnd            InetPortNumber,
    saRgFirewallPortFwdProto              INTEGER,
    saRgFirewallPortFwdSrvcName           SnmpAdminString,
    saRgFirewallPortFwdExternalPortStart  InetPortNumber,
    saRgFirewallPortFwdExternalPortEnd    InetPortNumber,
    }

saRgFirewallPortFwdIndex OBJECT-TYPE
    SYNTAX      INTEGER (1..30)
    MAX-ACCESS  not-accessible
    STATUS      current
    DESCRIPTION
            "The index"
    ::= { saRgFirewallPortFwdEntry 1 }

saRgFirewallPortFwdRowStatus OBJECT-TYPE
    SYNTAX      RowStatus
    MAX-ACCESS  read-write
    STATUS      current
    DESCRIPTION
            "The row status. A row can be destroyed.
             If the row is not used, set to notInService."
    ::= { saRgFirewallPortFwdEntry 2 }

saRgFirewallPortFwdToAddress OBJECT-TYPE
    SYNTAX      IpAddress
    MAX-ACCESS  read-write
    STATUS      current
    DESCRIPTION
            "Valid address must be entered for a row to be created."
    ::= { saRgFirewallPortFwdEntry 3 }

saRgFirewallPortFwdPortStart OBJECT-TYPE
    SYNTAX      InetPortNumber
    MAX-ACCESS  read-write
    STATUS      current
    DESCRIPTION
            "Valid port must be entered for a row to be created."
    ::= { saRgFirewallPortFwdEntry 4 }

saRgFirewallPortFwdPortEnd OBJECT-TYPE
    SYNTAX      InetPortNumber
    MAX-ACCESS  read-write
    STATUS      current
    DESCRIPTION
            "Valid port must be entered for a row to be created."
    ::= { saRgFirewallPortFwdEntry 5 }

saRgFirewallPortFwdProto OBJECT-TYPE
    SYNTAX      INTEGER {
        udp(1),
        tcp(2),
        udpTcp(3)
        }
    MAX-ACCESS  read-write
    STATUS      current
    DESCRIPTION
            ""
    DEFVAL { 2 }
    ::= { saRgFirewallPortFwdEntry 6 }

saRgFirewallPortFwdSrvcName OBJECT-TYPE
    SYNTAX      SnmpAdminString
    MAX-ACCESS  read-write
    STATUS      current
    DESCRIPTION
            "Port forward service name for use with Puma-based products."
    ::= { saRgFirewallPortFwdEntry 7 }

saRgFirewallPortFwdExternalPortStart OBJECT-TYPE
    SYNTAX      InetPortNumber
    MAX-ACCESS  read-write
    STATUS      current
    DESCRIPTION
            "Valid port must be entered for a row to be created. This is the outside-facing start port for the portforward."
    ::= { saRgFirewallPortFwdEntry 8 }

saRgFirewallPortFwdExternalPortEnd OBJECT-TYPE
    SYNTAX      InetPortNumber
    MAX-ACCESS  read-write
    STATUS      current
    DESCRIPTION
            "Valid port must be entered for a row to be created. This is the outside-facing end port for the portforward."
    ::= { saRgFirewallPortFwdEntry 9 }

-- Port triggering

saRgFirewallPortTrigTable OBJECT-TYPE
       SYNTAX      SEQUENCE OF SaRgFirewallPortTrigEntry
       MAX-ACCESS  not-accessible
       STATUS      current
       DESCRIPTION
               "This table is stored in non-vol and is empty
                after factory reset."
    ::= { saRgFirewall 7 }

saRgFirewallPortTrigEntry OBJECT-TYPE
    SYNTAX      SaRgFirewallPortTrigEntry
    MAX-ACCESS  not-accessible
    STATUS      current
    DESCRIPTION
            ""
    INDEX { saRgFirewallPortTrigIndex }
    ::= { saRgFirewallPortTrigTable 1 }

SaRgFirewallPortTrigEntry ::= SEQUENCE {
    saRgFirewallPortTrigIndex              INTEGER,
    saRgFirewallPortTrigRowStatus          RowStatus,
    saRgFirewallPortTrigTriggerPortStart   InetPortNumber,
    saRgFirewallPortTrigTriggerPortEnd     InetPortNumber,
    saRgFirewallPortTrigTargetPortStart    InetPortNumber,
    saRgFirewallPortTrigTargetPortEnd      InetPortNumber,
    saRgFirewallPortTrigProto              INTEGER,
    saRgFirewallPortTrigSrvcName           SnmpAdminString
    }

saRgFirewallPortTrigIndex OBJECT-TYPE
    SYNTAX      INTEGER (1..10)
    MAX-ACCESS  not-accessible
    STATUS      current
    DESCRIPTION
            "The index"
    ::= { saRgFirewallPortTrigEntry 1 }

saRgFirewallPortTrigRowStatus OBJECT-TYPE
    SYNTAX      RowStatus
    MAX-ACCESS  read-write
    STATUS      current
    DESCRIPTION
            "The row status. A row can be destroyed.
             If the row is not used, set to notInService."
    ::= { saRgFirewallPortTrigEntry 2 }


saRgFirewallPortTrigTriggerPortStart OBJECT-TYPE
    SYNTAX      InetPortNumber
    MAX-ACCESS  read-write
    STATUS      current
    DESCRIPTION
            ""
    ::= { saRgFirewallPortTrigEntry 3 }

saRgFirewallPortTrigTriggerPortEnd OBJECT-TYPE
    SYNTAX      InetPortNumber
    MAX-ACCESS  read-write
    STATUS      current
    DESCRIPTION
            ""
    ::= { saRgFirewallPortTrigEntry 4 }

saRgFirewallPortTrigTargetPortStart OBJECT-TYPE
    SYNTAX      InetPortNumber
    MAX-ACCESS  read-write
    STATUS      current
    DESCRIPTION
            ""
    ::= { saRgFirewallPortTrigEntry 5 }

saRgFirewallPortTrigTargetPortEnd OBJECT-TYPE
    SYNTAX      InetPortNumber
    MAX-ACCESS  read-write
    STATUS      current
    DESCRIPTION
            ""
    ::= { saRgFirewallPortTrigEntry 6 }

saRgFirewallPortTrigProto OBJECT-TYPE
    SYNTAX      INTEGER {
        udp(1),
        tcp(2),
        udpTcp(3)
        }
    MAX-ACCESS  read-write
    STATUS      current
    DESCRIPTION
            ""
    DEFVAL { 2 }
    ::= { saRgFirewallPortTrigEntry 7 }

saRgFirewallPortTrigSrvcName OBJECT-TYPE
    SYNTAX      SnmpAdminString
    MAX-ACCESS  read-write
    STATUS      current
    DESCRIPTION
            "Port trigger service name for use with Puma-based products."
    ::= { saRgFirewallPortTrigEntry 8 }

saRgFirewallHttpBlockingEnable OBJECT-TYPE
    SYNTAX      TruthValue
    MAX-ACCESS  read-write
    STATUS      current
    DESCRIPTION
        "Enables or disables firewall HTTP blocking on the device."
    DEFVAL { false }
    ::= { saRgFirewall 8 }

saRgFirewallP2pBlockingEnable OBJECT-TYPE
    SYNTAX      TruthValue
    MAX-ACCESS  read-write
    STATUS      current
    DESCRIPTION
        "Enables or disables firewall P2P blocking on the device."
    DEFVAL { false }
    ::= { saRgFirewall 9 }

saRgFirewallIdentBlockingEnable OBJECT-TYPE
    SYNTAX      TruthValue
    MAX-ACCESS  read-write
    STATUS      current
    DESCRIPTION
        "Enables or disables firewall ident blocking on the device."
    DEFVAL { false }
    ::= { saRgFirewall 10 }

saRgFirewallIcmpBlockingEnable OBJECT-TYPE
    SYNTAX      TruthValue
    MAX-ACCESS  read-write
    STATUS      current
    DESCRIPTION
        "Enables or disables firewall ICMP blocking on the device."
    DEFVAL { false }
    ::= { saRgFirewall 11 }

saRgFirewallMulticastBlockingEnable OBJECT-TYPE
    SYNTAX      TruthValue
    MAX-ACCESS  read-write
    STATUS      current
    DESCRIPTION
        "Enables or disables firewall multicast blocking on the device."
    DEFVAL { false }
    ::= { saRgFirewall 12 }

saRgFirewallApplySettings OBJECT-TYPE
    SYNTAX      TruthValue
    MAX-ACCESS  read-write
    STATUS      current
    DESCRIPTION
        "If set to true(1), then all the settings (MIB values)
         from this MIB tree will be applied to run time configuration,
         modifying previous RG operation with the new settings.
         Before setting the value to true, MIBs modified in the MIB
         tree are stored in non-vol and will not modify RG operation
         until saRgFirewallApplySettings is set to true or CM resets.
         Note: this applies only to the MIB objects that are stored
         in non-vol.
         Always returns false(2) when read."
    ::= { saRgFirewall 1001 }

saRgFirewallFactoryReset OBJECT-TYPE
    SYNTAX      TruthValue
    MAX-ACCESS  read-write
    STATUS      current
    DESCRIPTION
        "Set true(1) to restore default settings of firewall.
         Always returns false(2) when read."
    ::= { saRgFirewall 1002 }

-- ===
-- RIP
-- ===

saRgRip OBJECT IDENTIFIER ::=  { saRg 5 }

saRgRipBase OBJECT IDENTIFIER ::=  { saRgRip 1 }

saRgRipEnabled OBJECT-TYPE
    SYNTAX      TruthValue
    MAX-ACCESS  read-write
    STATUS      current
    DESCRIPTION
        "Enables or disables router information protocol support in the device."
    DEFVAL { false }
    ::= { saRgRipBase 1 }

saRgRipMd5AuthEnable    OBJECT-TYPE
    SYNTAX     TruthValue
    MAX-ACCESS read-write
    STATUS     current
    DESCRIPTION
        "Setting this object to true(1) causes the device to enable md5 auth"
    ::= { saRgRipBase 2 }

saRgRipMd5KeyId OBJECT-TYPE
    SYNTAX     INTEGER (0..255)
    MAX-ACCESS read-write
    STATUS     current
    DESCRIPTION
        "Key ID value for Md5 auth.
         This object return an empty string when read."
    ::= { saRgRipBase 3 }

saRgRipMd5KeyValue OBJECT-TYPE
    SYNTAX     OCTET STRING (SIZE(0..16))
    MAX-ACCESS read-write
    STATUS     current
    DESCRIPTION
        "MD5 Key Value"
    ::= { saRgRipBase 4 }

saRgRipInterval OBJECT-TYPE
    SYNTAX     INTEGER  (10..600)
    MAX-ACCESS read-write
    STATUS     current
    DESCRIPTION
        "Interval in Seconds for the Rip Reporting interval."
    ::= { saRgRipBase 5 }

saRgRipDestIpAddressType OBJECT-TYPE
    SYNTAX      InetAddressType
    MAX-ACCESS  read-write
    STATUS      current
    DESCRIPTION
        "The type of IP address assigned to the rgIpRipDestIpAddress."
    DEFVAL { ipv4 }
    ::= { saRgRipBase 6 }

saRgRipDestIpAddress OBJECT-TYPE
    SYNTAX      InetAddress
    MAX-ACCESS  read-write
    STATUS      current
    DESCRIPTION
        "Defines the RIP unicast destination IP Address for Rip Reports.
         If this value returns 0.0.0.0 then this is the default
         multicast IP address in the RFC (224.0.0.9)"
    ::= { saRgRipBase 7 }

saRgRipAuthType  OBJECT-TYPE
    SYNTAX      INTEGER {
        noAuth(1),
        simplePassword(2),
        md5(3)
        }
    MAX-ACCESS read-write
    STATUS     current
    DESCRIPTION
        "For use with puma-based products,
                NoAuth(1), no authentication,
                SimplePassword(2), simple plain password,
                MD5(3), md5 auth"
        DEFVAL { noAuth }
    ::= { saRgRipBase 8 }

saRgRipAuthSimplePassword OBJECT-TYPE
    SYNTAX     OCTET STRING
    MAX-ACCESS read-write
    STATUS     current
    DESCRIPTION
        "Simple password when auth type is 2"
    ::= { saRgRipBase 9 }


-- ==========================
-- DMS specific configuration
-- ==========================

-- this tree exists only if DMS hardware is present

saRgDmsSpecific OBJECT IDENTIFIER ::= { saRg 6 }

saRgDmsBase OBJECT IDENTIFIER ::= { saRgDmsSpecific 1 }

saRgDmsBaseSnmpPort OBJECT-TYPE
    SYNTAX      InetPortNumber
    MAX-ACCESS  read-write
    STATUS      current
    DESCRIPTION
            "Defines what port to use on the WAN IP address of the gateway
             to enable port forwarding for SNMP access to the DMS (on port
             161).
             Port 0 means port forwarding is disabled.
             Note: the entry for this does not appear in port forwarding
             table or on the web pages."
    DEFVAL { 0 }
    ::= { saRgDmsBase 1 }

saRgDmsBaseWebRedirect OBJECT-TYPE
    SYNTAX TruthValue
    MAX-ACCESS read-write
    STATUS current
    DESCRIPTION
         "This objects specifies if HTTP web page request should be
          redirected to DMS.
          The value of this object is stored in non-vol."
    DEFVAL { true }
    ::= { saRgDmsBase 2 }

saRgDmsProvisioning OBJECT IDENTIFIER ::= { saRgDmsSpecific 2 }

saRgDmsProvFilename OBJECT-TYPE
    SYNTAX SnmpAdminString
    MAX-ACCESS read-write
    STATUS current
    DESCRIPTION
        "Specifies the filename for DMS provisioning.
         The string is sent in DHCP OFFER and ACK as boot file to the DMS.
         If not set, boot file option is empty."
    DEFVAL { "" }
    ::= { saRgDmsProvisioning 1 }

saRgDmsProvServerType OBJECT-TYPE
    SYNTAX InetAddressType
    MAX-ACCESS read-write
    STATUS current
    DESCRIPTION
        "Specifies the type for IP address for DMS provisioning"
    DEFVAL { ipv4 }
    ::= { saRgDmsProvisioning 2 }

saRgDmsProvServer OBJECT-TYPE
    SYNTAX InetAddress
    MAX-ACCESS read-write
    STATUS current
    DESCRIPTION
        "Specifies the IP address for DMS provisioning.
         The address is sent in DHCP OFFER and ACK as next server to the DMS.
         If not set, the next server field is empty."
    DEFVAL  { '00000000'h }
    ::= { saRgDmsProvisioning 3 }

saRgDmsProvDhcpSecurity OBJECT-TYPE
    SYNTAX BITS {
        option-60(0),
        option-43-153(1)
        }
    MAX-ACCESS read-write
    STATUS current
    DESCRIPTION
        "Specifies what security features have to enabled for DMS
         to get the IP address from the gateway:
         0: SACMDMS must be present in DHCP DISCOVER option 60. If not set
            it is assumed there is no DMS. In this case the DMS will is
            treated as another CPE connected to LAN network.
         1: DHCP DISCOVER option 43.153 must be correct.
         This parameter is stored in non-vol and is 0x80 after factory
         reset."
    ::= { saRgDmsProvisioning 4 }


saRgDmsNameResolution OBJECT IDENTIFIER ::= { saRgDmsSpecific 3 }

saRgDmsNameResolutionName OBJECT-TYPE
    SYNTAX SnmpAdminString
    MAX-ACCESS read-write
    STATUS current
    DESCRIPTION
        "Specifies the DNS name for the DMS.
         Stored in non-vol and empty after factory reset."
    DEFVAL { "" }
    ::= { saRgDmsNameResolution 1 }

saRgDmsNameResolutionDeviceTarget OBJECT-TYPE
    SYNTAX INTEGER {
        disable(0),
        self(1),
        dms(2)
        }
    MAX-ACCESS read-write
    STATUS current
    DESCRIPTION
        "Specifies what IP address to resolve the name to.
         Stored in non-vol and set to disable(0) after factory reset."
    DEFVAL { 0 }
    ::= { saRgDmsNameResolution 2 }


-- ===========================
-- MoCA specific configuration
-- ===========================

saRgMocaExtSpecific OBJECT IDENTIFIER ::= { saRg 7 }

saRgMocaExtBase OBJECT IDENTIFIER ::= { saRgMocaExtSpecific 1 }

saRgMocaExtProvisioning OBJECT IDENTIFIER ::= { saRgMocaExtSpecific 2 }

saRgMocaExtProvFilename OBJECT-TYPE
    SYNTAX SnmpAdminString
    MAX-ACCESS read-write
    STATUS current
    DESCRIPTION
        "Specifies the filename for extender provisioning.
         The string is sent in DHCP OFFER and ACK as boot file to the extender.
         If not set, boot file option is empty."
    DEFVAL { "" }
    ::= { saRgMocaExtProvisioning 1 }

saRgMocaExtProvServerType OBJECT-TYPE
    SYNTAX InetAddressType
    MAX-ACCESS read-write
    STATUS current
    DESCRIPTION
        "Specifies the type for IP address for extender provisioning"
    DEFVAL { ipv4 }
    ::= { saRgMocaExtProvisioning 2 }

saRgMocaExtProvServer OBJECT-TYPE
    SYNTAX InetAddress
    MAX-ACCESS read-write
    STATUS current
    DESCRIPTION
        "Specifies the IP address for extender provisioning.
         The address is sent in DHCP OFFER and ACK as next server to the extender.
         If not set, the next server field is empty."
    DEFVAL  { '00000000'h } -- 0.0.0.0
    ::= { saRgMocaExtProvisioning 3 }



-- ===========
-- QoS related
-- ===========


SaRgQosTosToPriority ::= TEXTUAL-CONVENTION
    STATUS       current
    DESCRIPTION
         "Specifies mapping for each ToS value to 2-bit (4 value) priority.
          -h is the high significant bit, -l is the low significant bit."
    SYNTAX BITS {
        tos-fc-h(0),
        tos-fc-l(1),
        tos-f8-h(2),
        tos-f8-l(3),
        tos-f4-h(4),
        tos-f4-l(5),
        tos-f0-h(6),
        tos-f0-l(7),
        tos-ec-h(8),
        tos-ec-l(9),
        tos-e8-h(10),
        tos-e8-l(11),
        tos-e4-h(12),
        tos-e4-l(13),
        tos-e0-h(14),
        tos-e0-l(15),
        tos-dc-h(16),
        tos-dc-l(17),
        tos-d8-h(18),
        tos-d8-l(19),
        tos-d4-h(20),
        tos-d4-l(21),
        tos-d0-h(22),
        tos-d0-l(23),
        tos-cc-h(24),
        tos-cc-l(25),
        tos-c8-h(26),
        tos-c8-l(27),
        tos-c4-h(28),
        tos-c4-l(29),
        tos-c0-h(30),
        tos-c0-l(31),
        tos-bc-h(32),
        tos-bc-l(33),
        tos-b8-h(34),
        tos-b8-l(35),
        tos-b4-h(36),
        tos-b4-l(37),
        tos-b0-h(38),
        tos-b0-l(39),
        tos-ac-h(40),
        tos-ac-l(41),
        tos-a8-h(42),
        tos-a8-l(43),
        tos-a4-h(44),
        tos-a4-l(45),
        tos-a0-h(46),
        tos-a0-l(47),
        tos-9c-h(48),
        tos-9c-l(49),
        tos-98-h(50),
        tos-98-l(51),
        tos-94-h(52),
        tos-94-l(53),
        tos-90-h(54),
        tos-90-l(55),
        tos-8c-h(56),
        tos-8c-l(57),
        tos-88-h(58),
        tos-88-l(59),
        tos-84-h(60),
        tos-84-l(61),
        tos-80-h(62),
        tos-80-l(63),
        tos-7c-h(64),
        tos-7c-l(65),
        tos-78-h(66),
        tos-78-l(67),
        tos-74-h(68),
        tos-74-l(69),
        tos-70-h(70),
        tos-70-l(71),
        tos-6c-h(72),
        tos-6c-l(73),
        tos-68-h(74),
        tos-68-l(75),
        tos-64-h(76),
        tos-64-l(77),
        tos-60-h(78),
        tos-60-l(79),
        tos-5c-h(80),
        tos-5c-l(81),
        tos-58-h(82),
        tos-58-l(83),
        tos-54-h(84),
        tos-54-l(85),
        tos-50-h(86),
        tos-50-l(87),
        tos-4c-h(88),
        tos-4c-l(89),
        tos-48-h(90),
        tos-48-l(91),
        tos-44-h(92),
        tos-44-l(93),
        tos-40-h(94),
        tos-40-l(95),
        tos-3c-h(96),
        tos-3c-l(97),
        tos-38-h(98),
        tos-38-l(99),
        tos-34-h(100),
        tos-34-l(101),
        tos-30-h(102),
        tos-30-l(103),
        tos-2c-h(104),
        tos-2c-l(105),
        tos-28-h(106),
        tos-28-l(107),
        tos-24-h(108),
        tos-24-l(109),
        tos-20-h(110),
        tos-20-l(111),
        tos-1c-h(112),
        tos-1c-l(113),
        tos-18-h(114),
        tos-18-l(115),
        tos-14-h(116),
        tos-14-l(117),
        tos-10-h(118),
        tos-10-l(119),
        tos-0c-h(120),
        tos-0c-l(121),
        tos-08-h(122),
        tos-08-l(123),
        tos-04-h(124),
        tos-04-l(125),
        tos-00-h(126),
        tos-00-l(127)
        }

SaRgQosVlanToPriority ::= TEXTUAL-CONVENTION
    STATUS       current
    DESCRIPTION
         "Specifies mapping for each VLAN value to 2-bit (4 value) priorty.
          -h is the high significant bit, -l is the low significant bit."
    SYNTAX BITS {
        vlan-7-h(0),
        vlan-7-l(1),
        vlan-6-h(2),
        vlan-6-l(3),
        vlan-5-h(4),
        vlan-5-l(5),
        vlan-4-h(6),
        vlan-4-l(7),
        vlan-3-h(8),
        vlan-3-l(9),
        vlan-2-h(10),
        vlan-2-l(11),
        vlan-1-h(12),
        vlan-1-l(13),
        vlan-0-h(14),
        vlan-0-l(15)
    }

saRgQos OBJECT IDENTIFIER ::=  { saRg 8 }

saRgQosLan OBJECT IDENTIFIER ::=  { saRgQos 1 }

saRgQosLanBase OBJECT IDENTIFIER ::=  { saRgQosLan 1 }

saRgQosLanIgmpSnooping OBJECT-TYPE
    SYNTAX INTEGER {
        disable(0),
        enable(1)
        }
    MAX-ACCESS read-write
    STATUS current
    DESCRIPTION
        "Controls IGMP snooping feature on the LAN side."
    DEFVAL { 1 }
    ::= { saRgQosLanBase 1 }


saRgQosLanSwitch OBJECT IDENTIFIER ::=  { saRgQosLan 2 }

saRgQosLanSwitchPortIndex OBJECT-TYPE
    SYNTAX INTEGER (0..4)
    MAX-ACCESS not-accessible
    STATUS current
    DESCRIPTION
        "Port index in the switch. Index 0 is the connection to the router chip."
    ::= { saRgQosLanSwitch 1 }


saRgQosLanSwitchEgressScheduler OBJECT-TYPE
    SYNTAX INTEGER {
        sp(0),
        wrr(1),
        sp-wrr(2)
        }
    MAX-ACCESS read-write
    STATUS current
    DESCRIPTION
        "Sets the scheduling algorithm for egress queues on the switch.
         sp(0): use strict priority
         wrr(1): use weighted round robin, the weigths are 8, 4, 2, 1.
         sp-wrr(2): use SP for highest priority queue and WRR with weights
                    4, 2, 1 for lower priority queues."
    DEFVAL { 0 }
    ::= { saRgQosLanSwitch 2 }


saRgQosSwitchClassPriorityTable OBJECT-TYPE
       SYNTAX      SEQUENCE OF SaRgQosSwitchClassPriorityEntry
       MAX-ACCESS  not-accessible
       STATUS      current
       DESCRIPTION
               "This table determines which classifiers are used for frame
                priority determination in the switch."
    ::= { saRgQosLanSwitch 3 }

saRgQosSwitchClassPriorityEntry OBJECT-TYPE
    SYNTAX      SaRgQosSwitchClassPriorityEntry
    MAX-ACCESS  not-accessible
    STATUS      current
    DESCRIPTION
            ""
    INDEX { saRgQosLanSwitchPortIndex }
    ::= { saRgQosSwitchClassPriorityTable 1 }

SaRgQosSwitchClassPriorityEntry ::= SEQUENCE {
    saRgQosSwitchClassPriorityEnable  BITS,
    saRgQosSwitchClassPriorityPort    INTEGER,
    saRgQosSwitchClassPriorityDa      INTEGER,
    saRgQosSwitchClassPriorityVlan    INTEGER,
    saRgQosSwitchClassPriorityTos     INTEGER,
    saRgQosSwitchClassPrioritySetPort BITS,
    saRgQosSwitchClassPrioritySetDa   INTEGER,
    saRgQosSwitchClassPrioritySetVlan BITS,
    saRgQosSwitchClassPrioritySetTos  BITS
    }

saRgQosSwitchClassPriorityEnable OBJECT-TYPE
    SYNTAX BITS {
        port(0),
        dst-mac(1),
        vlan(2),
        tos(3)
    }
    MAX-ACCESS  not-accessible
    STATUS      current
    DESCRIPTION
            "Defines which classifiers to use for determinig egress frame priority.
             If more than one is selected, the order for classification is determined
             by the other MIB objects.
             port(0): priority is determined by the ingress port
             dst-mac(1): priority is determined by destination MAC address - not implemented
             vlan(2): priority is determined by IEEE 802.1p
             tos(3): priorty is determined by IP ToS (IPv4) or IP TC (IPv6)"
    DEFVAL { '20'h }
    ::= { saRgQosSwitchClassPriorityEntry 1 }

saRgQosSwitchClassPriorityPort OBJECT-TYPE
    SYNTAX      INTEGER (0..3)
    MAX-ACCESS  read-write
    STATUS      current
    DESCRIPTION
            "Defines priority of port classifier lookup.
             Priority 0 is the highest."
    DEFVAL { 2 }
    ::= { saRgQosSwitchClassPriorityEntry 2 }

saRgQosSwitchClassPriorityDa OBJECT-TYPE
    SYNTAX      INTEGER (0..3)
    MAX-ACCESS  not-accessible
    STATUS      current
    DESCRIPTION
            "Defines priority of DST MAC classifier lookup.
             Priority 0 is the highest.
             This is not implemented."
    DEFVAL { 3 }
    ::= { saRgQosSwitchClassPriorityEntry 3 }

saRgQosSwitchClassPriorityVlan OBJECT-TYPE
    SYNTAX      INTEGER (0..3)
    MAX-ACCESS  read-write
    STATUS      current
    DESCRIPTION
            "Defines priority of 802.1p classifier lookup.
             Priority 0 is the highest."
    DEFVAL { 0 }
    ::= { saRgQosSwitchClassPriorityEntry 4 }

saRgQosSwitchClassPriorityTos OBJECT-TYPE
    SYNTAX      INTEGER (0..3)
    MAX-ACCESS  read-write
    STATUS      current
    DESCRIPTION
            "Defines priority of ToS/TC classifier lookup.
             Priority 0 is the highest."
    DEFVAL { 1 }
    ::= { saRgQosSwitchClassPriorityEntry 5 }

saRgQosSwitchClassPrioritySetPort OBJECT-TYPE
    SYNTAX BITS {
        port-0-h(0),
        port-0-l(1),
        port-1-h(2),
        port-1-l(3),
        port-2-h(4),
        port-2-l(5),
        port-3-h(6),
        port-3-l(7),
        port-4-h(8),
        port-4-l(9)
        }
    MAX-ACCESS  read-write
    STATUS      current
    DESCRIPTION
            "This classifier sets the frame priority for defined ingress port.
             -h is the high significant bit, -l is the low significant bit."
    DEFVAL { '00'h }
    ::= { saRgQosSwitchClassPriorityEntry 6 }

saRgQosSwitchClassPrioritySetDa OBJECT-TYPE
    SYNTAX      INTEGER
    MAX-ACCESS  not-accessible
    STATUS      current
    DESCRIPTION
            "This is not implemented."
    DEFVAL { 0 }
    ::= { saRgQosSwitchClassPriorityEntry 7 }

saRgQosSwitchClassPrioritySetVlan OBJECT-TYPE
    SYNTAX      SaRgQosVlanToPriority
    MAX-ACCESS  read-write
    STATUS      current
    DESCRIPTION
            "This classifier sets the frame priority for each 802.1p priority."
    DEFVAL { 'fa50'h }
    ::= { saRgQosSwitchClassPriorityEntry 8 }

saRgQosSwitchClassPrioritySetTos OBJECT-TYPE
    SYNTAX      SaRgQosTosToPriority
    MAX-ACCESS  read-write
    STATUS      current
    DESCRIPTION
            "This classifier sets the frame priority for each ToS or TC."
    DEFVAL { 'ffffffffaaaaaaaa5555555500000000'h }
    ::= { saRgQosSwitchClassPriorityEntry 9 }


-- ================================
-- HomePlug AV specific information
-- ================================

saRgHomePlugAV OBJECT IDENTIFIER ::=  { saRg 9 }

saRgHomePlugAVBasicInfoTable OBJECT-TYPE
    SYNTAX SEQUENCE OF SaRgHomePlugAVBasicInfoEntry
    MAX-ACCESS      not-accessible
    STATUS          current
    DESCRIPTION
            "HomePlugAV basic information"
    ::= { saRgHomePlugAV 1 }

saRgHomePlugAVBasicInfoEntry OBJECT-TYPE
    SYNTAX          SaRgHomePlugAVBasicInfoEntry
    MAX-ACCESS      not-accessible
    STATUS          current
    DESCRIPTION
            "HomePlugAV basic information list"
    INDEX { saRgHPAVBasicInfoIndex }
    ::= { saRgHomePlugAVBasicInfoTable 1 }

 SaRgHomePlugAVBasicInfoEntry ::= SEQUENCE {
    saRgHPAVBasicInfoIndex        INTEGER,
    saRgHPAVBasicInfoNetworkID    OCTET STRING,
    saRgHPAVBasicInfoCCo          MacAddress
    }

saRgHPAVBasicInfoIndex OBJECT-TYPE
    SYNTAX          INTEGER (0..20)
    MAX-ACCESS      read-only
    STATUS          current
    DESCRIPTION
        "The index of HomePlugAV basic information"
    ::= { saRgHomePlugAVBasicInfoEntry 1 }

saRgHPAVBasicInfoNetworkID OBJECT-TYPE
    SYNTAX          OCTET STRING (SIZE(0..32))
    MAX-ACCESS      read-only
    STATUS          current
    DESCRIPTION
        "The information of network ID"
    ::= { saRgHomePlugAVBasicInfoEntry 2 }

saRgHPAVBasicInfoCCo OBJECT-TYPE
    SYNTAX          OCTET STRING (SIZE(0..32))
    MAX-ACCESS      read-only
    STATUS          current
    DESCRIPTION
        "The information of central coordinator"
    ::= { saRgHomePlugAVBasicInfoEntry 3 }

saRgHomePlugAVDeviceTable OBJECT-TYPE
    SYNTAX SEQUENCE OF SaRgHomePlugAVDeviceEntry
    MAX-ACCESS      not-accessible
    STATUS          current
    DESCRIPTION
            "HomePlugAV on the device side"
    ::= { saRgHomePlugAV 2 }

saRgHomePlugAVDeviceEntry OBJECT-TYPE
    SYNTAX          SaRgHomePlugAVDeviceEntry
    MAX-ACCESS      not-accessible
    STATUS          current
    DESCRIPTION
            "HomePlugAV list on the device side."
    INDEX { saRgHPAVBasicInfoIndex, saRgHPAVDeviceIndex }
    ::= { saRgHomePlugAVDeviceTable 1 }

SaRgHomePlugAVDeviceEntry ::= SEQUENCE {
    saRgHPAVDeviceIndex        INTEGER,
    saRgHPAVDeviceNetworkID    OCTET STRING,
    saRgHPAVDeviceCCo          MacAddress,
    saRgHPAVDeviceStatus       INTEGER,
    saRgHPAVDeviceMACAddr      MacAddress,
    saRgHPAVDeviceAdaptor      OCTET STRING,
    saRgHPAVDeviceVendor       OCTET STRING,
    saRgHPAVDeviceFirmware     OCTET STRING,
    saRgHPAVDeviceChipset      OCTET STRING,
    saRgHPAVDeviceTx           INTEGER,
    saRgHPAVDeviceRx           INTEGER,
    saRgHPAVDeviceTime         Integer32
    }

saRgHPAVDeviceIndex OBJECT-TYPE
    SYNTAX          INTEGER
    MAX-ACCESS      read-only
    STATUS          current
    DESCRIPTION
        "The index of the HomPlugAV on the device side"
    ::= { saRgHomePlugAVDeviceEntry 1 }

saRgHPAVDeviceStatus OBJECT-TYPE
    SYNTAX          INTEGER {
                        success(0),
                        failure(1)
                    }
    MAX-ACCESS      read-only
    STATUS          current
    DESCRIPTION
        "The status of HomPlugAV that indication if adaptor was discovered during last scan"
    ::= { saRgHomePlugAVDeviceEntry 2 }

saRgHPAVDeviceMACAddr OBJECT-TYPE
    SYNTAX          MacAddress
    MAX-ACCESS      read-only
    STATUS          current
    DESCRIPTION
        "MAC address assigned to dectected HP adaptor"
    ::= { saRgHomePlugAVDeviceEntry 3 }

saRgHPAVDeviceAdaptor OBJECT-TYPE
    SYNTAX          OCTET STRING (SIZE(0..6))
    MAX-ACCESS      read-only
    STATUS          current
    DESCRIPTION
        "Indication if the listed device is ether a local or remote HP adaptor"
    ::= { saRgHomePlugAVDeviceEntry 4 }

saRgHPAVDeviceVendor OBJECT-TYPE
    SYNTAX          OCTET STRING (SIZE(0..32))
    MAX-ACCESS      read-only
    STATUS          current
    DESCRIPTION
        "Textual representation of the manufacturer"
    ::= { saRgHomePlugAVDeviceEntry 5 }

saRgHPAVDeviceFirmware OBJECT-TYPE
    SYNTAX          OCTET STRING (SIZE(0..64))
    MAX-ACCESS      read-only
    STATUS          current
    DESCRIPTION
        "Textual representation of the firmware version of the HP adaptor"
    ::= { saRgHomePlugAVDeviceEntry 6 }

saRgHPAVDeviceChipset OBJECT-TYPE
    SYNTAX          OCTET STRING (SIZE(0..32))
    MAX-ACCESS      read-only
    STATUS          current
    DESCRIPTION
        "Textual representation of the chipset of HP adaptor"
    ::= { saRgHomePlugAVDeviceEntry 7 }

saRgHPAVDeviceTx OBJECT-TYPE
    SYNTAX          INTEGER
    MAX-ACCESS      read-only
    STATUS          current
    DESCRIPTION
        "Tx PHY rate as reported by the HP adaptor during the last scan [Mbps]"
    ::= { saRgHomePlugAVDeviceEntry 8 }

saRgHPAVDeviceRx OBJECT-TYPE
    SYNTAX          INTEGER
    MAX-ACCESS      read-only
    STATUS          current
    DESCRIPTION
        "Rx PHY rate as reported by the HP adaptor during the last scan [Mbps]"
    ::= { saRgHomePlugAVDeviceEntry 9 }

saRgHPAVDeviceTime OBJECT-TYPE
    SYNTAX          Integer32
    MAX-ACCESS      read-only
    STATUS          current
    DESCRIPTION
        "SysUpTime of the HGW when the table was last updated for this adaptor"
    ::= { saRgHomePlugAVDeviceEntry 10 }

saRgHomePlugAVHostTable OBJECT-TYPE
    SYNTAX SEQUENCE OF SaRgHomePlugAVHostEntry
    MAX-ACCESS      not-accessible
    STATUS          current
    DESCRIPTION
            "HomePlugAV on the host side"
    ::= { saRgHomePlugAV 3 }

saRgHomePlugAVHostEntry OBJECT-TYPE
    SYNTAX          SaRgHomePlugAVHostEntry
    MAX-ACCESS      not-accessible
    STATUS          current
    DESCRIPTION
            "HomePlugAV list on the host side."
    INDEX { saRgHPAVDHostIndex }
    ::= { saRgHomePlugAVHostTable 1 }

SaRgHomePlugAVHostEntry ::= SEQUENCE {
    saRgHPAVDHostIndex        INTEGER,
    saRgHPAVHostBridgedMAC    MacAddress
    }

saRgHPAVDHostIndex OBJECT-TYPE
    SYNTAX          INTEGER
    MAX-ACCESS      read-only
    STATUS          current
    DESCRIPTION
        "The index of the HomPlugAV on the device side"
    ::= { saRgHomePlugAVHostEntry 1 }

saRgHPAVHostBridgedMAC OBJECT-TYPE
    SYNTAX          MacAddress
    MAX-ACCESS      read-only
    STATUS          current
    DESCRIPTION
        "MAC address of the device behind the HP Apdator"
    ::= { saRgHomePlugAVHostEntry 2 }

saRgHomePlugAVPollRate OBJECT-TYPE
    SYNTAX          INTEGER
    MAX-ACCESS      read-write
    STATUS          current
    DESCRIPTION
            "Time between the different network scans"
    DEFVAL {0}
    ::=  { saRgHomePlugAV 4 }

saRgHomePlugAVClearTable OBJECT-TYPE
    SYNTAX          INTEGER {
                        disable (0),
                        enable (1)
                    }
    MAX-ACCESS      read-write
    STATUS          current
    DESCRIPTION
            "Clean content of the table and restart scan and scan schedule"
    DEFVAL {0}
    ::=  { saRgHomePlugAV 5 }

saRgHomePlugAVRefreshTable OBJECT-TYPE
    SYNTAX          INTEGER {
                        disable (0),
                        enable (1)
                    }
    MAX-ACCESS      read-write
    STATUS          current
    DESCRIPTION
            "Perform an additional scan without interfering with the scan schedule"
    DEFVAL {0}
    ::=  { saRgHomePlugAV 6 }

-- ================================
-- L2TP specific information
-- ================================

saRgL2TP OBJECT IDENTIFIER ::=  { saRg 10 }

saRgL2TPOperMode OBJECT-TYPE
    SYNTAX      INTEGER {
                l2TPDisable(0),
                l2TPv2client(1),
                l2TPv2server(2),
                l2TPv3client(3)
    }
    MAX-ACCESS  read-write
    STATUS      current
    DESCRIPTION
        "L2TPDisable(0) - Disables l2tp client or server Functionality
         L2TPv2client(1) - Enables l2tpv2 client Functionality
         L2TPv2server(2) - Enables l2tpv2 server Functionality
         L2TPv3client(3) - Enables l2tpv3 client Functionality"
     ::= { saRgL2TP 1 }

-- L2TPv2 Client Mode START

saRgL2TPv2Client OBJECT IDENTIFIER ::=  { saRgL2TP 2 }

saRgL2TPv2PPPServerAddressType OBJECT-TYPE
    SYNTAX      InetAddressType{
        unknown(0),
        ipv4(1),
        ipv6(2)
    }
    MAX-ACCESS  read-write
    STATUS      current
    DESCRIPTION
            "This MIB defines the type of internet address to be used for the L2TP Server.
            0:  An unknown address type.  This value MUST
                be used if the value of the corresponding
                InetAddress object is a zero-length string.
                It may also be used to indicate an IP address
                that is not in one of the formats defined
                below.
            1 : IPv4 L2TP Server Address
            2 : IPv6 L2TP Server Address (reserved for future support)
            NOTE: The default value of 1 indicates support for IPv4 IP address."
    DEFVAL { ipv4 }
    ::= { saRgL2TPv2Client 1 }

saRgL2TPv2PPPServerAddress OBJECT-TYPE
    SYNTAX      InetAddress
    MAX-ACCESS  read-write
    STATUS      current
    DESCRIPTION
            "IP address of the remote endpoint L2TP server."
    ::= { saRgL2TPv2Client 2 }


saRgL2TPv2PPPUsername OBJECT-TYPE
    SYNTAX      OCTET STRING (SIZE(0..32))
    MAX-ACCESS  read-write
    STATUS      current
    DESCRIPTION
            "PPPUsername as in the PPP Server user list"
    ::= { saRgL2TPv2Client 3 }


saRgL2TPv2PPPPassword OBJECT-TYPE
    SYNTAX      OCTET STRING (SIZE(0..32))
    MAX-ACCESS  read-write
    STATUS      current
    DESCRIPTION
            "PPPPassword set for the user on the PPP Server it is trying to connect"
    ::= { saRgL2TPv2Client 4 }

-- L2TPv2 Client Mode END

-- L2TPv2 Server Mode START

saRgL2TPv2Server OBJECT IDENTIFIER ::=  { saRgL2TP 3 }

saRgL2TPv2ClientTable OBJECT-TYPE
    SYNTAX SEQUENCE OF SaRgDeviceL2TPv2ClientEntry
    MAX-ACCESS not-accessible
    STATUS current
    DESCRIPTION
            "L2TP client table when saRgL2TPOperMode set to operate in l2tpv2 server mode "
    ::= { saRgL2TPv2Server 1 }

saRgL2TPv2ClientEntry OBJECT-TYPE
    SYNTAX      SaRgDeviceL2TPv2ClientEntry
    MAX-ACCESS  not-accessible
    STATUS     current
    DESCRIPTION
            ""
    INDEX { IMPLIED saRgL2TPv2ClientIndex }
    ::= { saRgL2TPv2ClientTable 1 }

SaRgDeviceL2TPv2ClientEntry ::= SEQUENCE {
    saRgL2TPv2ClientIndex       INTEGER,
    saRgL2TPv2ClientPppUsername OCTET STRING,
    saRgL2TPv2ClientPppPassword OCTET STRING
    }

saRgL2TPv2ClientIndex OBJECT-TYPE
    SYNTAX      INTEGER  (1..10)
    MAX-ACCESS  not-accessible
    STATUS      current
    DESCRIPTION
        "The unique index value of a row in this table."
    ::= { saRgL2TPv2ClientEntry 1 }


saRgL2TPv2ClientPppUsername OBJECT-TYPE
    SYNTAX      OCTET STRING (SIZE(0..32))
    MAX-ACCESS  read-write
    STATUS      current
    DESCRIPTION
            "Add the PPP username here. Remote client trying to connect should be present on this list"
    ::= { saRgL2TPv2ClientEntry 2 }

saRgL2TPv2ClientPppPassword OBJECT-TYPE
    SYNTAX      OCTET STRING (SIZE(0..32))
    MAX-ACCESS  read-write
    STATUS      current
    DESCRIPTION
            "Set the PPP user's password. Remote client trying to connect will be checked if it is a valid user"
    ::= { saRgL2TPv2ClientEntry 3 }

saRgL2TPv2ServerPreSharedPhrase OBJECT-TYPE
    SYNTAX      OCTET STRING (SIZE(0..32))
    MAX-ACCESS  read-write
    STATUS      current
    DESCRIPTION
            "Preshared Phrase needs to match between the server and the client in order for a tunnel to setup successfully"
    ::= { saRgL2TPv2Server 2 }

-- L2TPv2 Server Mode END


-- L2TPv3 Client Mode START

saRgL2TPv3Client OBJECT IDENTIFIER ::=  { saRgL2TP 4 }

saRgL2TPv3TunnelInterface OBJECT-TYPE
    SYNTAX    INTEGER {
                allEthernet(0),
                ethernet-1(1),
                ethernet-2(2),
                ethernet-3(3),
                ethernet-4(4),
                uSB(5),
                primarySSID(6),
                guestSSID-1(7),
                guestSSID-2(8),
                guestSSID-3(9),
                guestSSID-4(10),
                guestSSID-5(11),
                guestSSID-6(12),
                guestSSID-7(13)
    }
    MAX-ACCESS  read-write
    STATUS      current
    DESCRIPTION
            "allEthernet(0) represents the entire ethernet switch.
            ethernet-1 through ethernet-4 represent each individual ethernet switchport
            Sets the appropriate Tunnel endpoint interface.
            Note: USB(1) is for future support and must not be set"
    ::= { saRgL2TPv3Client 1 }

saRgL2TPv3Authentication OBJECT-TYPE
    SYNTAX  INTEGER {
            disable(0),
            enable(1)
        }
    MAX-ACCESS  read-write
    STATUS      current
    DESCRIPTION
            "Enable/ Disable Authentication used while setting up the tunnel"
    ::= { saRgL2TPv3Client 2 }

saRgL2TPv3DigestValue OBJECT-TYPE
    SYNTAX   Integer32{
                md5(0),
                sha-1(1)
    }
    MAX-ACCESS  read-write
    STATUS      current
    DESCRIPTION
            "Sets the appropriate Digest Value 0-MD5 or 1-SHA-1"
    ::= { saRgL2TPv3Client 3 }

saRgL2TPv3SharedSecret OBJECT-TYPE
    SYNTAX OCTET STRING (SIZE(0..32))
    MAX-ACCESS  read-write
    STATUS      current
    DESCRIPTION
            "Sets the Shared Secret to be used between server and client"
    ::= { saRgL2TPv3Client 4 }

saRgL2TPv3EndpointAddressType OBJECT-TYPE
    SYNTAX  InetAddressType{
        unknown(0),
        ipv4(1),
        ipv6(2)
    }
    MAX-ACCESS  read-write
    STATUS      current
    DESCRIPTION
            "This MIB defines the type of internet address to be used for the L2TP Server.
            0:  An unknown address type.  This value MUST
                be used if the value of the corresponding
                InetAddress object is a zero-length string.
                It may also be used to indicate an IP address
                that is not in one of the formats defined
                below.
            1 : IPv4 L2TP Server Address
            2 : IPv6 L2TP Server Address (reserved for future support)
            NOTE: The default value of 1 indicates support for IPv4 IP address."
    DEFVAL { ipv4 }
    ::= { saRgL2TPv3Client 5 }

saRgL2TPv3EndpointAddress OBJECT-TYPE
    SYNTAX InetAddress
    MAX-ACCESS  read-write
    STATUS      current
    DESCRIPTION
            "Set the Router's WAN MAN IP Address"
    ::= { saRgL2TPv3Client 6 }

saRgL2TPv3VirtualCircuitId OBJECT-TYPE
    SYNTAX   Integer32
    MAX-ACCESS  read-write
    STATUS      current
    DESCRIPTION
            "Sets the 32-bit Virtual Circuit Id(VC ID). for ex: 123"
    ::= { saRgL2TPv3Client 7 }

saRgL2TPv3CookieSize OBJECT-TYPE
    SYNTAX   Integer32{
                noCookie(0),
                size4(1),
                size8(2)
    }
    MAX-ACCESS  read-write
    STATUS      current
    DESCRIPTION
            "Sets the Cookie Size. for ex: 0 - No Cookie"
    ::= { saRgL2TPv3Client 8 }

saRgL2TPApplySettings OBJECT-TYPE
    SYNTAX      TruthValue
    MAX-ACCESS  read-write
    STATUS      current
    DESCRIPTION
        "If set to true(1), then RG will reboot and apply new L2TP settings.
         Before setting the value to true, MIBs modified in the MIB
         tree are stored in non-vol and will not modify RG operation
         until saRgL2TPApplySettings is set to true or CM resets.
         Note: this applies only to the MIB objects that are stored
         in non-vol.
         Always returns false(2) when read."
   ::= { saRgL2TP 5 }
-- L2TPv3 Client Mode END

-- ==================================
-- VLAN Tagging specific information
-- ==================================

saRgVlan OBJECT IDENTIFIER ::=  { saRg 11 }

saRgVlanStripTagsWan OBJECT-TYPE
    SYNTAX      TruthValue
    MAX-ACCESS  read-write
    STATUS      current
    DESCRIPTION
        "This MIB only strips the VLAN tags for upstream traffic (toward the CMTS) from
        CPEs connected directly to the ethernet switch ports. Upstream traffic from CPEs
        connected to the wireless interfaces will NOT have the VLAN tags removed."
        DEFVAL { true }
    ::= {  saRgVlan 1 }

saRgVlanStripTagsLan OBJECT-TYPE
    SYNTAX      TruthValue
    MAX-ACCESS  read-write
    STATUS      current
    DESCRIPTION
        "This MIB only strips the VLAN tags for downstream traffic (toward the LAN) to
         CPEs connected directly to the ethernet switch ports. Downstream traffic to CPEs
         connected to the wireless interfaces will not have the VLAN tags removed."
    DEFVAL { true }
    ::= {  saRgVlan 2 }


saRgVlanTable OBJECT-TYPE
    SYNTAX      SEQUENCE OF SaRgVlanEntry
    MAX-ACCESS  not-accessible
    STATUS      current
    DESCRIPTION
        "This table contains information specific to VLANs."
    REFERENCE
        "CableHome 1.1 Specification,Packet Handling & Address
        Translation section."
    ::= {  saRgVlan 3 }

saRgVlanEntry OBJECT-TYPE
    SYNTAX      SaRgVlanEntry
    MAX-ACCESS  not-accessible
    STATUS      current
    DESCRIPTION
        "List of individual VLAN entries."
    INDEX { saRgVlanID }
    ::= { saRgVlanTable 1 }

SaRgVlanEntry ::= SEQUENCE {
    saRgVlanID                      INTEGER,
    saRgVlanDesc                        OCTET STRING,
    saRgVlanEthernet            INTEGER,
    saRgVlanWiFi                        INTEGER,
    saRgVlanMoca                        INTEGER,
    saRgVlanUSB                     INTEGER,
    saRgVlanStartAddrType       InetAddressType,
    saRgVlanStartAddr           InetAddress,
    saRgVlanEndAddrType         InetAddressType,
    saRgVlanEndAddr                 InetAddress,
    saRgVlanSubnetMaskType      InetAddressType,
    saRgVlanSubnetMask          InetAddress,
    saRgVlanRouterIpType        InetAddressType,
    saRgVlanRouterIp            InetAddress,
    saRgVlanLeaseTime           INTEGER,
    saRgVlanRouteMode           INTEGER,
    saRgVlanTOS                     INTEGER,
    saRgVlanFirewall            TruthValue,
    saRgVlanUpnp                        TruthValue,
    saRgVlanRowStatus           RowStatus
}

saRgVlanID    OBJECT-TYPE
    SYNTAX    INTEGER   (2..1005)
    MAX-ACCESS  not-accessible
    STATUS      current
    DESCRIPTION
        "The ID of the VLAN Entry."
    ::= { saRgVlanEntry 1 }

saRgVlanDesc   OBJECT-TYPE
    SYNTAX OCTET STRING (SIZE(0..20))
    MAX-ACCESS read-write
    STATUS current
    DESCRIPTION
        "Description of this VLAN."
::= { saRgVlanEntry 2 }

saRgVlanEthernet    OBJECT-TYPE
    SYNTAX              INTEGER   (0..15)
    MAX-ACCESS  read-create
    STATUS      current
    DESCRIPTION
        "Assigns the Ethernet Port corresponding to the bit set to the VLAN.
         Bit 0 - Ethernet Port 1.
         Bit 1 - Ethernet Port 2.
         Bit 2 - Ethernet Port 3.
         Bit 3 - Ethernet Port 4."
    DEFVAL { 0 }
    ::= { saRgVlanEntry 3 }

saRgVlanWiFi    OBJECT-TYPE
    SYNTAX              INTEGER   (0..15)
    MAX-ACCESS  read-create
    STATUS      current
    DESCRIPTION
        "Assigns the WiFi BSSID corresponding to the bit set to the VLAN.
         Bit 0 - WiFi BSSID Port 0.
         Bit 1 - WiFi BSSID Port 1.
         Bit 2 - WiFi BSSID Port 2.
         Bit 3 - WiFi BSSID Port 3.
         ...
         Bit 15 - WiFi BSSID 15."
    DEFVAL { 0 }
    ::= { saRgVlanEntry 4 }

saRgVlanMoca    OBJECT-TYPE
    SYNTAX              INTEGER   (0..1)
    MAX-ACCESS  read-create
    STATUS      current
    DESCRIPTION
        "Include Moca on the VLAN."
    DEFVAL { 0 }
    ::= { saRgVlanEntry 5 }

saRgVlanUSB    OBJECT-TYPE
    SYNTAX              INTEGER   (0..1)
    MAX-ACCESS  read-create
    STATUS      current
    DESCRIPTION
        "Include USB on the VLAN."
    DEFVAL { 0 }
    ::= { saRgVlanEntry 6 }

saRgVlanStartAddrType OBJECT-TYPE
    SYNTAX      InetAddressType
    MAX-ACCESS  read-create
    STATUS      current
    DESCRIPTION
        "The start IP address range type."
    DEFVAL { ipv4 }
    ::= { saRgVlanEntry 7 }

saRgVlanStartAddr OBJECT-TYPE
    SYNTAX      InetAddress
    MAX-ACCESS  read-create
    STATUS      current
    DESCRIPTION
        "The start IP Address range."
    ::= { saRgVlanEntry 8 }

saRgVlanEndAddrType OBJECT-TYPE
    SYNTAX      InetAddressType
    MAX-ACCESS  read-create
    STATUS      current
    DESCRIPTION
        "The end IP address range type."
    DEFVAL { ipv4 }
    ::= { saRgVlanEntry 9}

saRgVlanEndAddr OBJECT-TYPE
    SYNTAX      InetAddress
    MAX-ACCESS  read-create
    STATUS      current
    DESCRIPTION
        "The end IP Address range."
    ::= { saRgVlanEntry 10}


saRgVlanSubnetMaskType OBJECT-TYPE
    SYNTAX      InetAddressType
    MAX-ACCESS  read-create
    STATUS      current
    DESCRIPTION
        "The subnet mask type."
    DEFVAL { ipv4 }
    ::= { saRgVlanEntry 11}

saRgVlanSubnetMask OBJECT-TYPE
    SYNTAX      InetAddress
    MAX-ACCESS  read-create
    STATUS      current
    DESCRIPTION
        "The subnet mask."
    ::= { saRgVlanEntry 12}

saRgVlanRouterIpType OBJECT-TYPE
    SYNTAX      InetAddressType
    MAX-ACCESS  read-create
    STATUS      current
    DESCRIPTION
        "The router IP type."
    DEFVAL { ipv4 }
    ::= { saRgVlanEntry 13}

saRgVlanRouterIp OBJECT-TYPE
    SYNTAX      InetAddress
    MAX-ACCESS  read-create
    STATUS      current
    DESCRIPTION
        "The router IP."
    ::= { saRgVlanEntry 14}

saRgVlanLeaseTime    OBJECT-TYPE
    SYNTAX              INTEGER
    MAX-ACCESS  read-create
    STATUS      current
    DESCRIPTION
        "The lease time for clients of this VLAN."
    DEFVAL { 3600 }
    ::= { saRgVlanEntry 15}

saRgVlanRouteMode    OBJECT-TYPE
    SYNTAX              INTEGER  {
          napt(1),
          bridged (2),
          routeddhcp(3)
          }
    MAX-ACCESS  read-create
    STATUS      current
    DESCRIPTION
        "The route mode for this VLAN.
        napt(1)   -- NAT with Port Translation Mode
        bridged (2)    -- Passthrough/Bridging Mode
        routeddhcp(3)  -- routed_dhcp"
    DEFVAL { 1 }
    ::= { saRgVlanEntry 16}

saRgVlanTOS    OBJECT-TYPE
    SYNTAX              INTEGER  (0..255)
    MAX-ACCESS  read-create
    STATUS      current
    DESCRIPTION
        "The Ethernet Frame TOS value for this VLAN."
    DEFVAL { 0 }
    ::= { saRgVlanEntry 17}

saRgVlanFirewall OBJECT-TYPE
    SYNTAX      TruthValue
    MAX-ACCESS  read-create
    STATUS      current
    DESCRIPTION
        "Include the firewall on this VLAN."
    DEFVAL { 1 }
    ::= { saRgVlanEntry 18}

saRgVlanUpnp OBJECT-TYPE
    SYNTAX      TruthValue
    MAX-ACCESS  read-create
    STATUS      current
    DESCRIPTION
        "Include the IGD UPnP on this VLAN."
    DEFVAL { true }
    ::= { saRgVlanEntry 19}

saRgVlanRowStatus OBJECT-TYPE
    SYNTAX      RowStatus
    MAX-ACCESS  read-create
    STATUS      current
    DESCRIPTION
          "The RowStatus interlock for the creation and deletion
        of a VLAN entry."
    ::= { saRgVlanEntry 20}

saRgVlanApplySettings OBJECT-TYPE
    SYNTAX      TruthValue
    MAX-ACCESS  read-write
    STATUS      current
    DESCRIPTION
        "If set to true(1), the current vlan MIB settings
         will be written to non-volatile storage and the VLAN Manager will
         re-initialize the networks using the new configuration.

         Unless this object is explicitly set to true(1), any settings made via
         other objects in this MIB will be lost if a reboot occurs.
         This MIB always returns false(2) when read."
    ::= {  saRgVlan 4 }

-- ==================================
-- DS Lite specific information
-- ==================================

saRgDslite OBJECT IDENTIFIER ::=  { saRg 12 }

saRgDsliteOption OBJECT-TYPE
    SYNTAX INTEGER {
                disable(0),
        option-64(1)
                }
    MAX-ACCESS  read-write
    STATUS      current
    DESCRIPTION
        "This MIB will toggle whether DHCPv6 option 64 is requested in the solicit.
                 The option should only be requested if DS Lite is enabled."
        DEFVAL { 1 }
    ::= {  saRgDslite 1 }

saRgDsliteAftrName OBJECT-TYPE
    SYNTAX SnmpAdminString
    MAX-ACCESS  read-write
    STATUS      current
    DESCRIPTION
        "This MIB will read/write the remote IPv6 FQDN of the AFTR router in
                 the DS Lite tunnel configuration.
                 This should only have an effect if eRouter is in IPv6 only mode and DS Lite is enabled."
    ::= {  saRgDslite 2 }

saRgDsliteAftrAddress OBJECT-TYPE
    SYNTAX InetAddressIPv6
    MAX-ACCESS  read-write
    STATUS      current
    DESCRIPTION
        "This MIB will set the remote IPv6 address of the AFTR router manually in
                 the DS Lite tunnel configuration.
                 This should only have an effect if eRouter is in IPv6 only mode and DS Lite is enabled."
    ::= {  saRgDslite 3 }

saRgDsliteTcpMssClamping OBJECT-TYPE
    SYNTAX      INTEGER (0..1420)
    MAX-ACCESS  read-write
    STATUS      current
    DESCRIPTION
        "Specifies  whether TCP MSS clamping is enabled on the interface.
         0 disables clamping, 1 clamps the MSS depending on the
         interface MTU. A value > 1 will be used as clamping size.
                 This MIB takes effect immediately and does not require saRgDsliteApplySettings."
    DEFVAL { 0 }
    ::= { saRgDslite 4 }

saRgDsliteIPv4FragEnabled OBJECT-TYPE
    SYNTAX      TruthValue
    MAX-ACCESS  read-write
    STATUS      current
    DESCRIPTION
        "Enables or disable IPv4 fragmentation in DS-Lite.
                This MIB takes effect immediately and does not require saRgDsliteApplySettings."
    DEFVAL { False }
::= { saRgDslite 5 }

saRgDslitePcpMode OBJECT-TYPE
    SYNTAX      TruthValue
    MAX-ACCESS  read-write
    STATUS      current
    DESCRIPTION
        "This MIB controls the PCP operation mode for DS-Lite.
                False: plain mode, our client will not accept port-mapping messages from a PCP server.
                True: encapsulation mode, our client will accept port-mapping messages from a PCP server.
                "
    DEFVAL { False }
::= { saRgDslite 6 }

saRgDsliteApplySettings OBJECT-TYPE
    SYNTAX      TruthValue
    MAX-ACCESS  read-write
    STATUS      current
    DESCRIPTION
        "If set to true(1), then all the settings (MIB values)
         from this MIB tree will be applied to the runtime configuration,
         This will resolve the AFTR domain name to the AFTR IPv6 address,
                 and initialize the DSlite tunnel. This will initialize using the AFTR
                 address if both the address and FQDN are defined.
                 This should only activate the tunnel if eRouter is in IPv6 only mode
                 and DS Lite is enabled.
         Always returns false(2) when read."
    ::= { saRgDslite 1001 }

-- ==================================
-- Wifi Hotspot Specific Information
-- ==================================

saRgWifiHotspotMib OBJECT IDENTIFIER ::= { saRg 13 }

saRgWifiHotspotBase OBJECT IDENTIFIER ::= { saRgWifiHotspotMib 1 }

saRgWifiHotspotEnabled OBJECT-TYPE
    SYNTAX      TruthValue
    MAX-ACCESS  read-write
    STATUS      current
    DESCRIPTION
        "Enables or disable Wifi Hotspot support in the device."
   ::= { saRgWifiHotspotBase 1 }

saRgWifiHotspotTable OBJECT-TYPE
    SYNTAX      SEQUENCE OF SaRgWifiHotspotEntry
    MAX-ACCESS  not-accessible
    STATUS      current
    DESCRIPTION
        "A table used to configure settings related to Wi-fi Hotspot."
    ::= { saRgWifiHotspotBase 2 }

saRgWifiHotspotEntry OBJECT-TYPE
    SYNTAX      SaRgWifiHotspotEntry
    MAX-ACCESS  not-accessible
    STATUS      current
    DESCRIPTION
         "An entry defining the Wi-fi hotspot characteristics of an
          individual Wi-Fi network interface."
    INDEX   { saRgWifiHotspotIf }
    ::= { saRgWifiHotspotTable 1 }

SaRgWifiHotspotEntry ::=
    SEQUENCE    {
        saRgWifiHotspotInstance              Unsigned32,
        saRgWifiHotspotIf                    INTEGER,
        saRgWifiHotspotMode                  INTEGER,
        saRgWifiHotspotCpeIdleTimeout        Unsigned32,
        saRgWifiHotspotCpeSessionTimeout     Unsigned32,
        saRgWifiHotspotRadiusAccAddressType  InetAddressType,
        saRgWifiHotspotRadiusAccAddress      InetAddress,
        saRgWifiHotspotRadiusAccPort         InetPortNumber,
        saRgWifiHotspotRadiusAccKey          DisplayString,
        saRgWifiHotspotPacketFilterMask      Unsigned32,
        saRgWifiHotspotInsertDhcpOptionsMask Unsigned32,
        saRgWifiHotspotRowStatus             RowStatus,
		saRgWifiHotspotRadiusAccInterimInterval Unsigned32
    }


saRgWifiHotspotInstance    OBJECT-TYPE
    SYNTAX      Unsigned32
    MAX-ACCESS  not-accessible
    STATUS      current
    DESCRIPTION
        "The key for a unique instance of this object."
    ::= { saRgWifiHotspotEntry 1 }

saRgWifiHotspotIf OBJECT-TYPE
    SYNTAX      INTEGER {
                        wifi1-0(1),
                        wifi1-1(2),
                        wifi1-2(3),
                        wifi1-3(4),
                        wifi1-4(5),
                        wifi1-5(6),
                        wifi1-6(7),
                        wifi1-7(8),
                        wifi2-0(9),
                        wifi2-1(10),
                        wifi2-2(11),
                        wifi2-3(12),
                        wifi2-4(13),
                        wifi2-5(14),
                        wifi2-6(15),
                        wifi2-7(16)
        }
    MAX-ACCESS  read-create
    STATUS      current
    DESCRIPTION
        "Wi-fi network interface."
    ::= { saRgWifiHotspotEntry 2 }

saRgWifiHotspotMode OBJECT-TYPE
    SYNTAX      INTEGER {
                disable(1),
                enableBridge(2),
                enableL2oGre(3)
    }
    MAX-ACCESS  read-create
    STATUS      current
    DESCRIPTION
        "Wi-fi Hotsot mode:
         enableBridge - Wi-Fi traffic will be bridged
         enableL2oGre - Wi-Fi traffic will be sent over GRE tunnel.
                        GRE Tunnel should be configured and enabled."
    ::= { saRgWifiHotspotEntry 3 }

saRgWifiHotspotCpeIdleTimeout OBJECT-TYPE
    SYNTAX      Unsigned32
    MAX-ACCESS  read-create
    STATUS      current
    DESCRIPTION
        "CPE inactivity/idle timeout in seconds which will trigger disconnect.
         Value of 0 will disable inactivity tracking."
    ::= { saRgWifiHotspotEntry 4 }

saRgWifiHotspotCpeSessionTimeout OBJECT-TYPE
    SYNTAX      Unsigned32
    MAX-ACCESS  read-create
    STATUS      current
    DESCRIPTION
        "CPE maximum session duration timeout in seconds.
         Value of 0 will disable tracking session duration."
    ::= { saRgWifiHotspotEntry 5 }

saRgWifiHotspotRadiusAccAddressType OBJECT-TYPE
    SYNTAX      InetAddressType
    MAX-ACCESS  read-create
    STATUS      current
    DESCRIPTION
        "The type of internet address used for saRgWifiHotspotRadiusAccAddress."
    ::= { saRgWifiHotspotEntry 6 }

saRgWifiHotspotRadiusAccAddress OBJECT-TYPE
    SYNTAX      InetAddress
    MAX-ACCESS  read-create
    STATUS      current
    DESCRIPTION
        "The internet address of the RADIUS Accounting server for this service set."
    ::= { saRgWifiHotspotEntry 7 }

saRgWifiHotspotRadiusAccPort OBJECT-TYPE
    SYNTAX      InetPortNumber
    MAX-ACCESS  read-create
    STATUS      current
    DESCRIPTION
        "The UDP port used to communicate with the RADIUS Accounting server.
         Default value set to 1813."
    DEFVAL { 1813 }
    ::= { saRgWifiHotspotEntry 8 }

saRgWifiHotspotRadiusAccKey OBJECT-TYPE
    SYNTAX      DisplayString
    MAX-ACCESS  read-create
    STATUS      current
    DESCRIPTION
        "The RADIUS Accounting server shared security key."
    ::= { saRgWifiHotspotEntry 9 }

saRgWifiHotspotPacketFilterMask OBJECT-TYPE
    SYNTAX      Unsigned32
    MAX-ACCESS  read-create
    STATUS      current
    DESCRIPTION
        "Bit mask for limiting traffic to certain packet types.
         Possible value:
         11111111 11111111 11111111 11111111: Allow All traffic
         xxxxxxxx xxxxxxxx xxxxxxxx xxxxxxx1: Allow IPv4 (0x0800) packets
         xxxxxxxx xxxxxxxx xxxxxxxx xxxxxx1x: Allow IPv6 (0x86dd) packets
         xxxxxxxx xxxxxxxx xxxxxxxx xxxxx1xx: Allow IPx  (0x8137) packets
         xxxxxxxx xxxxxxxx xxxxxxxx xxxx1xxx: Allow ARP  (0x0806) packets
         xxxxxxxx xxxxxxxx xxxxxxxx xxx1xxxx: Allow RARP (0x8035) packets
         xxxxxxxx xxxxxxxx xxxxxxxx xx1xxxxx: Allow VLAN (0x8100) packets
         "
    ::= { saRgWifiHotspotEntry 10 }

saRgWifiHotspotInsertDhcpOptionsMask OBJECT-TYPE
    SYNTAX      Unsigned32
    MAX-ACCESS  read-create
    STATUS      current
    DESCRIPTION
        "Bit mask for inserting DHCP options in DHCP Discover/Request packet from
         connected wifi client device.
         Possible value:
         0x1: Insert DHCP relay agent option 82.
              circuit-id sub-option: AP-MAC-ADDRESS;SSID-NAME;SSID-TYPE
         0x2: Insert DHCP relay agent option 82.
              remote-id  sub-option: String containing MAC address of connected
                                     wifi client device in the format XX:XX:XX:XX:XX:XX.
         0x4: Insert/Modify DHCP option 60 with string containing SSID Name.
		 0x8: Enables/Disables CM MAC address (format XX:XX:XX:XX:XX:XX) included in DHCP option 82.2 remote-id"
    ::= { saRgWifiHotspotEntry 11 }

saRgWifiHotspotRowStatus OBJECT-TYPE
    SYNTAX RowStatus
    MAX-ACCESS read-create
    STATUS current
    DESCRIPTION
        "The RowStatus interlock for the creation and deletion
        can be modified at any time while the row is active(1)."
    ::= { saRgWifiHotspotEntry 12 }

saRgWifiHotspotRadiusAccInterimInterval OBJECT-TYPE 
    SYNTAX      Unsigned32 
    MAX-ACCESS  read-create 
    STATUS      current 
    DESCRIPTION 
              "Setting to control interval between each RADIUS interim update in seconds. 
              Feature may be disabled by setting to zero, else minimum value is 60" 
	DEFVAL { 900 }
    ::= { saRgWifiHotspotEntry 13 }

saRgWifiHotspotAutRateLimit OBJECT-TYPE
    SYNTAX      Unsigned32
    MAX-ACCESS  read-write
    STATUS      current
    DESCRIPTION
        "Authentication rate limit in messages per second. If client exceeds
         this limit, authentication from the client is ignored for
         saRgWifiHotspotAutDenialTimeout."
   ::= { saRgWifiHotspotBase 3 }

saRgWifiHotspotAutDenialTimeout OBJECT-TYPE
    SYNTAX      Unsigned32
    MAX-ACCESS  read-write
    STATUS      current
    DESCRIPTION
        "Timeout in seconds during which authentication from a client is ignored
         once authentication message rate exceeds saRgWifiHotspotAutRateLimit."
   ::= { saRgWifiHotspotBase 4 }

saRgWifiHotspotRadiusOrigIf OBJECT-TYPE
    SYNTAX      INTEGER {
                eRouter(1),
                cm(2)
        }
    MAX-ACCESS  read-write
    STATUS      current
    DESCRIPTION
        "Originating interface of radius authentication and accounting traffic."
    ::= { saRgWifiHotspotBase 5 }

saRgWifiHotspotIgnoreMaxCpeSetting OBJECT-TYPE
    SYNTAX      TruthValue
    MAX-ACCESS  read-write
    STATUS      current
    DESCRIPTION
        "This setting is applicable for wifi hotspot bridged mode.
         When set to true(1), clients connected through the hotspot wifi will not be
         counted when enforcing the 'Maximum CPE devices' on DOCSIS."
   ::= { saRgWifiHotspotBase 6 }

saRgWifiHotspotCapable OBJECT-TYPE
    SYNTAX      TruthValue
    MAX-ACCESS  read-write
    STATUS      current
    DESCRIPTION
        "Returns whether the device is capable of WiFi HotSpot functionality."
   ::= { saRgWifiHotspotBase 7 }

saRgWifiHotspotConnectedClientsTable OBJECT-TYPE
    SYNTAX      SEQUENCE OF SaRgWifiHotspotConnectedClientsEntry
    MAX-ACCESS  not-accessible
    STATUS      current
    DESCRIPTION
        "Clients table connected to Wi-fi Hotspot."
    ::= { saRgWifiHotspotBase 8 }

saRgWifiHotspotConnectedClientsEntry OBJECT-TYPE
    SYNTAX      SaRgWifiHotspotConnectedClientsEntry
    MAX-ACCESS  not-accessible
    STATUS      current
    DESCRIPTION
         "An entry defining the Wi-fi hotspot connected clients"
    INDEX   { saRgWifiHotspotIf, saRgWifiHotspotConnectedClientsIndex }
    ::= { saRgWifiHotspotConnectedClientsTable 1 }

SaRgWifiHotspotConnectedClientsEntry ::=
    SEQUENCE    {
        saRgWifiHotspotConnectedClientsIndex              INTEGER,
                saRgWifiHotspotConnectedClientsPhysAddr                   PhysAddress,
        saRgWifiHotspotConnectedClientsRssiLevel          Integer32,
                saRgWifiHotspotConnectedClientsIpv4Addr                   IpAddress,
                saRgWifiHotspotConnectedClientsHostName           SnmpAdminString,
                saRgWifiHotspotConnectedClientsDhcpv4Status               INTEGER,
    }

saRgWifiHotspotConnectedClientsIndex    OBJECT-TYPE
    SYNTAX      INTEGER
    MAX-ACCESS  not-accessible
    STATUS      current
    DESCRIPTION
        "The index of the client connected to specific hotspot ssid."
    ::= { saRgWifiHotspotConnectedClientsEntry 1 }

saRgWifiHotspotConnectedClientsPhysAddr OBJECT-TYPE
    SYNTAX      PhysAddress
    MAX-ACCESS  read-only
    STATUS      current
    DESCRIPTION
            "MAC address of the client connected to the Hotspot SSID"
    ::= { saRgWifiHotspotConnectedClientsEntry 2 }

saRgWifiHotspotConnectedClientsRssiLevel OBJECT-TYPE
    SYNTAX      Integer32
    MAX-ACCESS  read-only
    STATUS      current
    DESCRIPTION
            "Signal strength of the Hotspot client in dBm"
    ::= { saRgWifiHotspotConnectedClientsEntry 3 }

saRgWifiHotspotConnectedClientsIpv4Addr OBJECT-TYPE
    SYNTAX      IpAddress
    MAX-ACCESS  read-only
    STATUS      current
    DESCRIPTION
            "IPv4 address obtained by the client from Hotspot DHCP server"
    ::= { saRgWifiHotspotConnectedClientsEntry 4 }

saRgWifiHotspotConnectedClientsHostName OBJECT-TYPE
    SYNTAX      SnmpAdminString
    MAX-ACCESS  read-only
    STATUS      current
    DESCRIPTION
            "Hostname of the client based on DHCP option 12."
    ::= { saRgWifiHotspotConnectedClientsEntry 5 }

saRgWifiHotspotConnectedClientsDhcpv4Status OBJECT-TYPE
    SYNTAX      INTEGER  {
                                        discover(1),
                                        offer(2),
                                        request(3),
                                        ack(4),
                                        nack(5)
                        }
    MAX-ACCESS  read-only
    STATUS      current
    DESCRIPTION
            "DHCPv4 status of the Hotspot client."
    ::= { saRgWifiHotspotConnectedClientsEntry 6 }

saRgWifiHotspotDisablePMKCaching OBJECT-TYPE     
    SYNTAX      TruthValue
    MAX-ACCESS  read-write
    STATUS      current
    DESCRIPTION
        "Enables or disable WPA2 PMK Caching. By default this feature is enable"
	DEFVAL { true }
   ::= { saRgWifiHotspotBase 9 }

saRgWifiHotspotConnectionSpeedMin OBJECT-TYPE     
    SYNTAX      Unsigned32
    MAX-ACCESS  read-write
    STATUS      current
    DESCRIPTION
        "Minimum connection speed in kbps required by client to maintain connectivity."
   ::= { saRgWifiHotspotBase 10 }

saRgWifiHotspotConnectionSpeedTimeout OBJECT-TYPE     
    SYNTAX      Unsigned32
    MAX-ACCESS  read-write
    STATUS      current
    DESCRIPTION
        "Timeout in seconds during which client is allowed to maintain connectivity
         once connection speed is below saRgWifiHotspotConnectionSpeedMin. When timeout
         expires client is disassociated."
   ::= { saRgWifiHotspotBase 11 }
   
-- ====================================================
-- L2oGRE tunnel for Wifi Hotspot specific information
-- ====================================================

saRgL2ogreMib OBJECT IDENTIFIER ::= { saRg 14 }

saRgL2ogreBase OBJECT IDENTIFIER ::= { saRgL2ogreMib 1 }

saRgL2ogreEnabled OBJECT-TYPE
    SYNTAX      TruthValue
    MAX-ACCESS  read-write
    STATUS      current
    DESCRIPTION
        "Enables or disable GRE Tunnel support in the device."
    DEFVAL { false }
   ::= { saRgL2ogreBase 1 }

saRgL2ogrePriRemoteAddressType OBJECT-TYPE
    SYNTAX      InetAddressType
    MAX-ACCESS  read-write
    STATUS      current
    DESCRIPTION
        "The IP address type (ipv4, ipv6 or dns) of primary remote
         endpoint of the GRE tunnel."
    DEFVAL { ipv4 }
    ::= { saRgL2ogreBase 2 }

saRgL2ogrePriRemoteAddress OBJECT-TYPE
    SYNTAX      InetAddress
    MAX-ACCESS  read-write
    STATUS      current
    DESCRIPTION
        "IP address or FQDN of primary remote endpoint of the GRE tunnel."
    ::= { saRgL2ogreBase 3 }

saRgL2ogreSecRemoteAddressType OBJECT-TYPE
    SYNTAX      InetAddressType
    MAX-ACCESS  read-write
    STATUS      current
    DESCRIPTION
        "The IP address type (ipv4, ipv6 or dns) of secondary remote
         endpoint of the GRE tunnel."
    DEFVAL { ipv4 }
    ::= { saRgL2ogreBase 4 }

saRgL2ogreSecRemoteAddress OBJECT-TYPE
    SYNTAX      InetAddress
    MAX-ACCESS  read-write
    STATUS      current
    DESCRIPTION
        "IP address or FQDN of secondary remote endpoint of the GRE tunnel."
    ::= { saRgL2ogreBase 5 }

saRgL2ogreDSCP OBJECT-TYPE
    SYNTAX      Integer32 (0..63)
    MAX-ACCESS  read-write
    STATUS      current
    DESCRIPTION
        "The method is used to set the high 6 bits of TOS in the
         IPv4 header or traffic class in IPv6 header."
    ::= { saRgL2ogreBase 6 }

saRgL2ogreKeepAliveMode OBJECT-TYPE
    SYNTAX      INTEGER {
                disabled(1),
                ping(2),
                ping-noswitchover(3)
    }
    MAX-ACCESS  read-write
    STATUS      current
    DESCRIPTION
        "Keepalive modes for failover mechanism.
         ping - Use ICMP pings within tunnel as a keepalive messages."
    ::= { saRgL2ogreBase 7 }

saRgL2ogreKeepAliveCount OBJECT-TYPE
    SYNTAX      Integer32
    MAX-ACCESS  read-write
    STATUS      current
    DESCRIPTION
        "Number of keep-alive messages sent at regular interval."
    ::= { saRgL2ogreBase 8 }

saRgL2ogreKeepAliveInterval OBJECT-TYPE
    SYNTAX      Integer32
    MAX-ACCESS  read-write
    STATUS      current
    DESCRIPTION
        "Interval in seconds between keep-alive messages."
    ::= { saRgL2ogreBase 9 }

saRgL2ogreKeepAliveFailureThreshold OBJECT-TYPE
    SYNTAX      Integer32
    MAX-ACCESS  read-write
    STATUS      current
    DESCRIPTION
        "Number of keep-alive failures that will cause fail-over."
    ::= { saRgL2ogreBase 10 }

saRgL2ogreStatsTable OBJECT-TYPE
    SYNTAX      SEQUENCE OF SaRgL2ogreStatsEntry
    MAX-ACCESS  not-accessible
    STATUS      current
    DESCRIPTION
        "This table provides statistical information of GRE tunnel."
    ::= { saRgL2ogreBase 11 }

saRgL2ogreStatsEntry OBJECT-TYPE
    SYNTAX      SaRgL2ogreStatsEntry
    MAX-ACCESS  not-accessible
    STATUS      current
    DESCRIPTION
        "This table provides statistical information of GRE tunnel."
    INDEX { saRgL2ogreStatsIndex }
    ::= { saRgL2ogreStatsTable 1 }

SaRgL2ogreStatsEntry ::= SEQUENCE {
    saRgL2ogreStatsIndex                    Integer32,
    saRgL2ogreStatsBytesSent                Counter64,
    saRgL2ogreStatsBytesReceived            Counter64,
    saRgL2ogreStatsPacketsSent              Counter64,
    saRgL2ogreStatsPacketsReceived          Counter64,
    saRgL2ogreStatsDiscardPacketsReceived   Counter64,
    saRgL2ogreStatsErrorPacketsReceived     Counter64,
    saRgL2ogreStatsKeepAliveSent            Counter64,
    saRgL2ogreStatsKeepAliveReceived        Counter64,
    saRgL2ogreStatsRowStatus                RowStatus
}

saRgL2ogreStatsIndex OBJECT-TYPE
    SYNTAX      Integer32 (1..256)
    MAX-ACCESS  not-accessible
    STATUS      current
    DESCRIPTION
        "Table index"
    ::= { saRgL2ogreStatsEntry 1 }

saRgL2ogreStatsBytesSent OBJECT-TYPE
    SYNTAX      Counter64
    MAX-ACCESS  read-only
    STATUS      current
    DESCRIPTION
        "Number bytes sent."
    ::= { saRgL2ogreStatsEntry 2 }

saRgL2ogreStatsBytesReceived OBJECT-TYPE
    SYNTAX      Counter64
    MAX-ACCESS  read-only
    STATUS      current
    DESCRIPTION
        "Number bytes received."
    ::= { saRgL2ogreStatsEntry 3 }

saRgL2ogreStatsPacketsSent OBJECT-TYPE
    SYNTAX      Counter64
    MAX-ACCESS  read-only
    STATUS      current
    DESCRIPTION
        "Number packets sent."
    ::= { saRgL2ogreStatsEntry 4 }

saRgL2ogreStatsPacketsReceived OBJECT-TYPE
    SYNTAX      Counter64
    MAX-ACCESS  read-only
    STATUS      current
    DESCRIPTION
        "Number packets received."
    ::= { saRgL2ogreStatsEntry 5 }

saRgL2ogreStatsDiscardPacketsReceived OBJECT-TYPE
    SYNTAX      Counter64
    MAX-ACCESS  read-only
    STATUS      current
    DESCRIPTION
        "Number packets received that were discarded.
         Because source network interface is down."
    ::= { saRgL2ogreStatsEntry 6 }

saRgL2ogreStatsErrorPacketsReceived OBJECT-TYPE
    SYNTAX      Counter64
    MAX-ACCESS  read-only
    STATUS      current
    DESCRIPTION
        "Number packets received that were in error.
         Because tunnel packets are not correct type.
         Eg. Received IP packet instead of L2 packets."
    ::= { saRgL2ogreStatsEntry 7 }

saRgL2ogreStatsKeepAliveSent OBJECT-TYPE
    SYNTAX      Counter64
    MAX-ACCESS  read-only
    STATUS      current
    DESCRIPTION
        "Number keepalive packets sent."
    ::= { saRgL2ogreStatsEntry 8 }

saRgL2ogreStatsKeepAliveReceived OBJECT-TYPE
    SYNTAX      Counter64
    MAX-ACCESS  read-only
    STATUS      current
    DESCRIPTION
        "Number keepalive packets received."
    ::= { saRgL2ogreStatsEntry 9 }

saRgL2ogreSourceIfTable OBJECT-TYPE
    SYNTAX      SEQUENCE OF SaRgL2ogreSourceIfEntry
    MAX-ACCESS  not-accessible
    STATUS      current
    DESCRIPTION
        "This table contains information specific to network source interface
         whose traffic is mapped into GRE tunnel."
    ::= { saRgL2ogreBase 12 }

saRgL2ogreSourceIfEntry OBJECT-TYPE
    SYNTAX      SaRgL2ogreSourceIfEntry
    MAX-ACCESS  not-accessible
    STATUS      current
    DESCRIPTION
        "List of individual source interface entries mapped into GRE tunnel."
    INDEX { saRgL2ogreSourceIfInstance }
    ::= { saRgL2ogreSourceIfTable 1 }

SaRgL2ogreSourceIfEntry ::= SEQUENCE {
    saRgL2ogreSourceIfInstance           Unsigned32,
    saRgL2ogreSourceIf                   INTEGER,
    saRgL2ogreSourceIfEnabled            TruthValue,
    saRgL2ogreSourceIfVlanTag            Integer32,
    saRgL2ogreSourceIfMplsHeader         Integer32,
    saRgL2ogreSourceIfRowStatus          RowStatus
}

saRgL2ogreSourceIfInstance    OBJECT-TYPE
    SYNTAX      Unsigned32
    MAX-ACCESS  not-accessible
    STATUS      current
    DESCRIPTION
        "The key for a unique instance of this object."
    ::= {saRgL2ogreSourceIfEntry 1 }

saRgL2ogreSourceIf OBJECT-TYPE
    SYNTAX      INTEGER {
                        wifi1-0(1),
                        wifi1-1(2),
                        wifi1-2(3),
                        wifi1-3(4),
                        wifi1-4(5),
                        wifi1-5(6),
                        wifi1-6(7),
                        wifi1-7(8),
                        wifi2-0(9),
                        wifi2-1(10),
                        wifi2-2(11),
                        wifi2-3(12),
                        wifi2-4(13),
                        wifi2-5(14),
                        wifi2-6(15),
                        wifi2-7(16)
        }
    MAX-ACCESS  read-create
    STATUS      current
    DESCRIPTION
        "Source interface whose traffic will be pass through GRE tunnel."
    ::= { saRgL2ogreSourceIfEntry 2 }

saRgL2ogreSourceIfEnabled OBJECT-TYPE
    SYNTAX      TruthValue
    MAX-ACCESS  read-create
    STATUS      current
    DESCRIPTION
        "Enables or disable mapping traffic from network interface into GRE tunnel."
   ::= { saRgL2ogreSourceIfEntry 3 }

saRgL2ogreSourceIfVlanTag OBJECT-TYPE
    SYNTAX      Integer32
    MAX-ACCESS  read-create
    STATUS      current
    DESCRIPTION
        "Add VLAN tag consists of 16bit of Tag Protocol Identifier (TPID)
         and 16 bit of Tag Control Identifier (TCI).
         Value of 0 will disable adding VLAN tag.
         Tag Protocol Identifier (TPID) should set to 0x8100."
    ::= { saRgL2ogreSourceIfEntry 4 }

saRgL2ogreSourceIfMplsHeader OBJECT-TYPE
    SYNTAX      Integer32
    MAX-ACCESS  read-create
    STATUS      current
    DESCRIPTION
        "MPLS Header. Value of 0 will disable adding MPLS Header."
    ::= { saRgL2ogreSourceIfEntry 5 }

saRgL2ogreSourceIfRowStatus OBJECT-TYPE
    SYNTAX      RowStatus
    MAX-ACCESS  read-create
    STATUS      current
    DESCRIPTION
        "The RowStatus interlock for the creation and deletion of a table entry."
    ::= { saRgL2ogreSourceIfEntry 6 }

saRgL2ogreOrigIf OBJECT-TYPE
    SYNTAX      INTEGER {
                eRouter(1)
               }
    MAX-ACCESS  read-write
    STATUS      current
    DESCRIPTION
        "Originating Interface of GRE tunnel."
    ::= { saRgL2ogreBase 13 }

saRgL2ogreConcentratorServiceName OBJECT-TYPE
    SYNTAX      DisplayString
    MAX-ACCESS  read-write
    STATUS      current
    DESCRIPTION
        "FQDN of GRE tunnel concentrator/gw service.
         If this is set then, DNS Query of type SRV will be used for discovering
         FQDN of primary and secondary remote endpoint of GRE tunnel."
    ::= { saRgL2ogreBase 14 }

saRgL2ogreDnsResolverRetryTimerMin OBJECT-TYPE
    SYNTAX      Unsigned32
    MAX-ACCESS  read-write
    STATUS      current
    DESCRIPTION
        "Minimum timeout interval in seconds before retrying DNS query."
    ::= { saRgL2ogreBase 15 }

saRgL2ogreDnsResolverRetryTimerMax OBJECT-TYPE
    SYNTAX      Unsigned32
    MAX-ACCESS  read-write
    STATUS      current
    DESCRIPTION
        "Maximum timeout interval in seconds before retrying DNS query."
    ::= { saRgL2ogreBase 16 }

saRgL2ogreKeepAliveFailureInterval OBJECT-TYPE
    SYNTAX      Integer32
    MAX-ACCESS  read-write
    STATUS      current
    DESCRIPTION
        "Configured interval between pings for WLAN GW when disabled due to both WLAN GWs failing."
    ::= { saRgL2ogreBase 17 }

saRgL2ogreKeepAliveReattemptInterval OBJECT-TYPE
    SYNTAX      Integer32
    MAX-ACCESS  read-write
    STATUS      current
    DESCRIPTION
        "Configured interval to reattempt connection to a primary WLAN GW even when secondary WLAN GW is available and clients are connected."
    ::= { saRgL2ogreBase 18 }

saRgIGMP OBJECT IDENTIFIER ::= { saRg 15 }

saRgIGMPMaxRspTime OBJECT-TYPE
    SYNTAX INTEGER {
        IGMPv2(1),
        IGMPv3(2)
        }
    MAX-ACCESS  read-write
    STATUS      current
    DESCRIPTION
        "There is a difference in IGMPv2 and IGMPv3 to translate the MAX RSP CODE to MAX RSP TIME.
                 In IGMPv2 “MAX RSP TIME” = “MAX RSP CODE”/10.
                 In IGMPv3, When Max RSP Code > 128, max response time is calculated differently.
                 When this MIB is set to IGMPv2(1) modem will set max response time according to IGMPv2 standard.
                 This setting is recommended for older CMTS implementations and when random response time of 0 to 10 sec is desired.
                 When this MIB is set to IGMPv3(2) modem will set max response time according to IGMPv3 standard.
                 This setting is recommended for new CMTS implementations and when random response time of 0 to above 10 seconds is desired.
         This object is stored in non-vol and defaults to IGMPv2(1) after factory reset."
        DEFVAL { 1 }
    ::= { saRgIGMP 1 }


-- ====================================================
-- Network Extender Status MIB
-- ====================================================

saRgNetworkExtenders OBJECT IDENTIFIER ::= { saRg 16 }

saRgNetworkExtenderTable  OBJECT-TYPE
    SYNTAX      SEQUENCE OF SaRgNetworkExtenderEntry
    MAX-ACCESS  not-accessible
    STATUS      current
    DESCRIPTION
        "Multiple Attached Network Extender Table. Maximum of 8 Entries"

    ::= { saRgNetworkExtenders 1 }

saRgNetworkExtenderEntry OBJECT-TYPE
    SYNTAX      SaRgNetworkExtenderEntry
    MAX-ACCESS  not-accessible
    STATUS      current
    DESCRIPTION
        "A row in the table which represents information about attached Network Extender."
    INDEX   { saRgNetworkExtenderIndex }
    ::= { saRgNetworkExtenderTable 1 }

SaRgNetworkExtenderEntry ::= SEQUENCE {
      saRgNetworkExtenderIndex                INTEGER,
      saRgNetworkExtenderIpAddress            IpAddress,
      saRgNetworkExtenderDeviceName           OCTET STRING,
      saRgNetworkExtenderVenderName           OCTET STRING,
      saRgNetworkExtenderModelNumber          OCTET STRING,
      saRgNetworkExtenderFirmwareVersion      OCTET STRING
    }

saRgNetworkExtenderIndex OBJECT-TYPE
    SYNTAX      INTEGER (1..8)
    MAX-ACCESS  not-accessible
    STATUS      current
    DESCRIPTION
        "The index of the the table.  Up to 8 connected devices supported"
    ::= { saRgNetworkExtenderEntry 1 }

saRgNetworkExtenderIpAddress OBJECT-TYPE
    SYNTAX      IpAddress
    MAX-ACCESS  read-only
    STATUS      current
    DESCRIPTION
        "The IP Address of the Device"
    ::= { saRgNetworkExtenderEntry 2 }

saRgNetworkExtenderDeviceName OBJECT-TYPE
    SYNTAX      OCTET STRING (SIZE(0..32))
    MAX-ACCESS  read-only
    STATUS      current
    DESCRIPTION
        "The Name of the Device as returned by HNAP"
    ::= { saRgNetworkExtenderEntry 3 }

saRgNetworkExtenderVenderName OBJECT-TYPE
    SYNTAX      OCTET STRING (SIZE(0..32))
    MAX-ACCESS  read-only
    STATUS      current
    DESCRIPTION
        "The Vender Name as returned by HNAP"
    ::= { saRgNetworkExtenderEntry 4 }

saRgNetworkExtenderModelNumber OBJECT-TYPE
    SYNTAX      OCTET STRING (SIZE(0..32))
    MAX-ACCESS  read-only
    STATUS      current
    DESCRIPTION
        "The Model Number of the Device as returned by HNAP"
    ::= { saRgNetworkExtenderEntry 5 }

saRgNetworkExtenderFirmwareVersion OBJECT-TYPE
    SYNTAX      OCTET STRING (SIZE(0..32))
    MAX-ACCESS  read-only
    STATUS      current
    DESCRIPTION
        "The Firmware version of the Device as returned by HNAP"
    ::= { saRgNetworkExtenderEntry 6 }

-- ====================================================
-- Network Extender Radio Status Table
-- ====================================================

saRgNetworkExtenderRadioTable  OBJECT-TYPE
    SYNTAX      SEQUENCE OF SaRgNetworkExtenderRadioEntry
    MAX-ACCESS  not-accessible
    STATUS      current
    DESCRIPTION
        "Attached Network Extender Radio Table. Maximum of 32 entries (per extender).
        If the attached device has no radios/SSID, this table will be empty"
    ::= { saRgNetworkExtenders 2 }

saRgNetworkExtenderRadioEntry OBJECT-TYPE
    SYNTAX      SaRgNetworkExtenderRadioEntry
    MAX-ACCESS  not-accessible
    STATUS      current
    DESCRIPTION
        "A row in the table for Network Extender attached WiFi Radios."
    INDEX       {   saRgNetworkExtenderIndex,
                                saRgNetworkExtenderRadioIndex }
    ::= { saRgNetworkExtenderRadioTable 1 }

SaRgNetworkExtenderRadioEntry ::= SEQUENCE {
        saRgNetworkExtenderRadioIndex           INTEGER,
        saRgNetworkExtenderRadioSSID            OCTET STRING,
        saRgNetworkExtenderRadioBSSID           PhysAddress,
        saRgNetworkExtenderRadioChannel         OCTET STRING,
        saRgNetworkExtenderRadioMode            OCTET STRING
    }

saRgNetworkExtenderRadioIndex OBJECT-TYPE
    SYNTAX      INTEGER (1..32)
    MAX-ACCESS  not-accessible
    STATUS      current
    DESCRIPTION
        "The index of the radio/SSID. Up to 32 SSIDs supported"
    ::= { saRgNetworkExtenderRadioEntry 1 }

saRgNetworkExtenderRadioSSID OBJECT-TYPE
    SYNTAX      OCTET STRING (SIZE(0..32))
    MAX-ACCESS  read-only
    STATUS      current
    DESCRIPTION
        "The SSID of the radio as by HNAP"
    ::= { saRgNetworkExtenderRadioEntry 2 }

saRgNetworkExtenderRadioBSSID OBJECT-TYPE
    SYNTAX      PhysAddress
    MAX-ACCESS  read-only
    STATUS      current
    DESCRIPTION
        "The BSSID as reported by HNAP"
    ::= { saRgNetworkExtenderRadioEntry 3 }

saRgNetworkExtenderRadioChannel OBJECT-TYPE
    SYNTAX      OCTET STRING (SIZE(0..32))
    MAX-ACCESS  read-only
    STATUS      current
    DESCRIPTION
        "Returns the Primary Radio Channel Number as reported by HNAP"
    ::= { saRgNetworkExtenderRadioEntry 4 }

saRgNetworkExtenderRadioMode OBJECT-TYPE
    SYNTAX      OCTET STRING (SIZE(0..32))
    MAX-ACCESS  read-only
    STATUS      current
    DESCRIPTION
        "Returns the Radio Operational Mode as reported by HNAP"
    ::= { saRgNetworkExtenderRadioEntry 5 }

-- ====================================================
-- Network Extender Connected Client Table
-- ====================================================
saRgNetworkExtenderClientTable  OBJECT-TYPE
    SYNTAX      SEQUENCE OF SaRgNetworkExtenderClientEntry
    MAX-ACCESS  not-accessible
    STATUS      current
    DESCRIPTION
        "Attached Network Extender Client Table. Maximum of 64 Entries per Extender"
    ::= { saRgNetworkExtenders 3 }

saRgNetworkExtenderClientEntry OBJECT-TYPE
    SYNTAX      SaRgNetworkExtenderClientEntry
    MAX-ACCESS  not-accessible
    STATUS      current
    DESCRIPTION
        "A row in the table denoting Network Extender Clients."
    INDEX       {   saRgNetworkExtenderIndex,
                    saRgNetworkExtenderClientIndex }
    ::= { saRgNetworkExtenderClientTable  1 }

SaRgNetworkExtenderClientEntry ::= SEQUENCE {
         saRgNetworkExtenderClientIndex          INTEGER,
         saRgNetworkExtenderClientMAC            PhysAddress,
         saRgNetworkExtenderClientInterface      OCTET STRING
    }

saRgNetworkExtenderClientIndex OBJECT-TYPE
    SYNTAX      INTEGER (1..64)
    MAX-ACCESS  not-accessible
    STATUS      current
    DESCRIPTION
        "The index of the Client."
    ::= { saRgNetworkExtenderClientEntry 1 }


saRgNetworkExtenderClientMAC OBJECT-TYPE
    SYNTAX      PhysAddress
    MAX-ACCESS  read-only
    STATUS      current
    DESCRIPTION
        "Returns the client's MAC as reported by HNAP"
    ::= { saRgNetworkExtenderClientEntry 2 }

saRgNetworkExtenderClientInterface OBJECT-TYPE
    SYNTAX      OCTET STRING (SIZE(0..32))
    MAX-ACCESS  read-only
    STATUS      current
    DESCRIPTION
        "Returns the client's connected interface per HNAP.   Wifi-2.4, Wifi-5.0, Ethernet, etc"
    ::= { saRgNetworkExtenderClientEntry 3 }

END
